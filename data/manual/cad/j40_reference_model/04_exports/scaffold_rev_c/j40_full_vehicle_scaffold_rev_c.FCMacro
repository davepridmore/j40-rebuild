# J40 full vehicle CAD scaffold Rev C
# Units: millimetres. Run inside FreeCAD.
# Right-hand drive layout for left-side traffic; positive Y is the driver side.
# Generated by tools/generate_j40_full_vehicle_cad_scaffold.py.
import FreeCAD as App
import Part
import Mesh

try:
    import FreeCADGui as Gui
except Exception:
    Gui = None

doc = App.newDocument('j40_full_vehicle_scaffold_rev_c')
groups = {}

TRANSPARENCY_BY_GROUP = {
    'glass': 60,
    'hard_top': 18,
    'datum': 45,
    'as_fitted_routes': 15,
    'mechanical_clearance': 72,
}

def group_for(group_name):
    group = groups.get(group_name)
    if group is None:
        group = doc.addObject('App::DocumentObjectGroup', group_name)
        group.Label = group_name.replace('_', ' ').title()
        groups[group_name] = group
    return group

def set_color(obj, rgb, group_name):
    if hasattr(obj, 'ViewObject'):
        obj.ViewObject.ShapeColor = rgb
        obj.ViewObject.Transparency = TRANSPARENCY_BY_GROUP.get(group_name, 0)

def add_to_group(obj, group_name):
    group_for(group_name).addObject(obj)
    return obj

def add_box(group_name, name, x, y_center, z, length, width, height, rgb):
    shape = Part.makeBox(length, width, height, App.Vector(x, y_center - width / 2, z))
    obj = doc.addObject('Part::Feature', name)
    obj.Shape = shape
    obj.Label = name.replace('_', ' ')
    set_color(obj, rgb, group_name)
    return add_to_group(obj, group_name)

def add_cylinder(group_name, name, x, y, z, axis, diameter, length, rgb):
    if axis == 'x':
        vector = App.Vector(1, 0, 0)
        base = App.Vector(x - length / 2, y, z)
    elif axis == 'y':
        vector = App.Vector(0, 1, 0)
        base = App.Vector(x, y - length / 2, z)
    else:
        vector = App.Vector(0, 0, 1)
        base = App.Vector(x, y, z - length / 2)
    obj = doc.addObject('Part::Feature', name)
    obj.Shape = Part.makeCylinder(diameter / 2, length, base, vector)
    obj.Label = name.replace('_', ' ')
    set_color(obj, rgb, group_name)
    return add_to_group(obj, group_name)

def add_wheel(group_name, name, x, y_center, z, diameter, width):
    tire = doc.addObject('Part::Feature', name + '_tire')
    tire.Shape = Part.makeCylinder(diameter / 2, width, App.Vector(x, y_center - width / 2, z), App.Vector(0, 1, 0))
    tire.Label = name.replace('_', ' ') + ' tire'
    set_color(tire, (0.03, 0.03, 0.03), group_name)
    add_to_group(tire, group_name)
    rim = doc.addObject('Part::Feature', name + '_rim')
    rim.Shape = Part.makeCylinder(diameter * 0.26, width + 8, App.Vector(x, y_center - (width + 8) / 2, z), App.Vector(0, 1, 0))
    rim.Label = name.replace('_', ' ') + ' rim'
    set_color(rim, (0.72, 0.72, 0.72), group_name)
    add_to_group(rim, group_name)
    hub = doc.addObject('Part::Feature', name + '_hub')
    hub.Shape = Part.makeCylinder(diameter * 0.15, width + 14, App.Vector(x, y_center - (width + 14) / 2, z), App.Vector(0, 1, 0))
    hub.Label = name.replace('_', ' ') + ' hub'
    set_color(hub, (0.10, 0.10, 0.10), group_name)
    add_to_group(hub, group_name)
    return tire

def add_mesh(group_name, name, vertices, faces, rgb):
    mesh = Mesh.Mesh()
    for face in faces:
        if len(face) < 3:
            continue
        first = App.Vector(*vertices[face[0]])
        for index in range(1, len(face) - 1):
            mesh.addFacet(first, App.Vector(*vertices[face[index]]), App.Vector(*vertices[face[index + 1]]))
    obj = doc.addObject('Mesh::Feature', name)
    obj.Mesh = mesh
    obj.Label = name.replace('_', ' ')
    set_color(obj, rgb, group_name)
    return add_to_group(obj, group_name)

add_box('chassis', 'left_frame_rail', 360, -390, 430, 3140, 85, 120, (0.176, 0.188, 0.200))
add_box('chassis', 'right_frame_rail', 360, 390, 430, 3140, 85, 120, (0.176, 0.188, 0.200))
add_box('chassis', 'crossmember_1', 450, 0, 455, 85, 880, 95, (0.176, 0.188, 0.200))
add_box('chassis', 'crossmember_2', 980, 0, 455, 85, 880, 95, (0.176, 0.188, 0.200))
add_box('chassis', 'crossmember_3', 1660, 0, 455, 85, 880, 95, (0.176, 0.188, 0.200))
add_box('chassis', 'crossmember_4', 2420, 0, 455, 85, 880, 95, (0.176, 0.188, 0.200))
add_box('chassis', 'crossmember_5', 3230, 0, 455, 85, 880, 95, (0.176, 0.188, 0.200))
add_box('chassis', 'front_bumper', 20, 0, 525, 165, 1620, 120, (0.067, 0.075, 0.082))
add_box('chassis', 'rear_bumper', 3665, 0, 530, 145, 1550, 110, (0.067, 0.075, 0.082))
add_cylinder('chassis', 'front_left_tow_ring', 75, -430, 450, 'x', 115, 28, (0.722, 0.722, 0.722))
add_cylinder('chassis', 'front_right_tow_ring', 75, 430, 450, 'x', 115, 28, (0.722, 0.722, 0.722))
add_box('running_gear', 'front_axle_tube', 735, 0, 395, 90, 1560, 90, (0.722, 0.722, 0.722))
add_box('running_gear', 'rear_axle_tube', 3020, 0, 395, 90, 1560, 90, (0.722, 0.722, 0.722))
add_box('running_gear', 'front_left_leaf_spring', 215, -430, 335, 1050, 65, 55, (0.133, 0.133, 0.133))
add_box('running_gear', 'front_right_leaf_spring', 215, 430, 335, 1050, 65, 55, (0.133, 0.133, 0.133))
add_box('running_gear', 'rear_left_leaf_spring', 2500, -430, 335, 1050, 65, 55, (0.133, 0.133, 0.133))
add_box('running_gear', 'rear_right_leaf_spring', 2500, 430, 335, 1050, 65, 55, (0.133, 0.133, 0.133))
add_wheel('running_gear', 'front_left_tire', 735, -705, 395, 790, 250)
add_wheel('running_gear', 'front_right_tire', 735, 705, 395, 790, 250)
add_wheel('running_gear', 'rear_left_tire', 3020, -705, 395, 790, 250)
add_wheel('running_gear', 'rear_right_tire', 3020, 705, 395, 790, 250)
add_box('running_gear', 'front_left_mud_tire_outer_lug_1', 1110, -705, 395, 95, 48, 58, (0.114, 0.114, 0.114))
add_box('running_gear', 'front_left_mud_tire_outer_lug_2', 1081.45, -705, 538.506, 95, 48, 58, (0.114, 0.114, 0.114))
add_box('running_gear', 'front_left_mud_tire_outer_lug_3', 1000.17, -705, 660.165, 95, 48, 58, (0.114, 0.114, 0.114))
add_box('running_gear', 'front_left_mud_tire_outer_lug_4', 878.506, -705, 741.455, 95, 48, 58, (0.114, 0.114, 0.114))
add_box('running_gear', 'front_left_mud_tire_outer_lug_5', 735, -705, 770, 95, 48, 58, (0.114, 0.114, 0.114))
add_box('running_gear', 'front_left_mud_tire_outer_lug_6', 591.494, -705, 741.455, 95, 48, 58, (0.114, 0.114, 0.114))
add_box('running_gear', 'front_left_mud_tire_outer_lug_7', 469.835, -705, 660.165, 95, 48, 58, (0.114, 0.114, 0.114))
add_box('running_gear', 'front_left_mud_tire_outer_lug_8', 388.545, -705, 538.506, 95, 48, 58, (0.114, 0.114, 0.114))
add_box('running_gear', 'front_left_mud_tire_outer_lug_9', 360, -705, 395, 95, 48, 58, (0.114, 0.114, 0.114))
add_box('running_gear', 'front_left_mud_tire_outer_lug_10', 388.545, -705, 251.494, 95, 48, 58, (0.114, 0.114, 0.114))
add_box('running_gear', 'front_left_mud_tire_outer_lug_11', 469.835, -705, 129.835, 95, 48, 58, (0.114, 0.114, 0.114))
add_box('running_gear', 'front_left_mud_tire_outer_lug_12', 591.494, -705, 48.5452, 95, 48, 58, (0.114, 0.114, 0.114))
add_box('running_gear', 'front_left_mud_tire_outer_lug_13', 735, -705, 20, 95, 48, 58, (0.114, 0.114, 0.114))
add_box('running_gear', 'front_left_mud_tire_outer_lug_14', 878.506, -705, 48.5452, 95, 48, 58, (0.114, 0.114, 0.114))
add_box('running_gear', 'front_left_mud_tire_outer_lug_15', 1000.17, -705, 129.835, 95, 48, 58, (0.114, 0.114, 0.114))
add_box('running_gear', 'front_left_mud_tire_outer_lug_16', 1081.45, -705, 251.494, 95, 48, 58, (0.114, 0.114, 0.114))
add_box('running_gear', 'front_right_mud_tire_outer_lug_1', 1110, 705, 395, 95, 48, 58, (0.114, 0.114, 0.114))
add_box('running_gear', 'front_right_mud_tire_outer_lug_2', 1081.45, 705, 538.506, 95, 48, 58, (0.114, 0.114, 0.114))
add_box('running_gear', 'front_right_mud_tire_outer_lug_3', 1000.17, 705, 660.165, 95, 48, 58, (0.114, 0.114, 0.114))
add_box('running_gear', 'front_right_mud_tire_outer_lug_4', 878.506, 705, 741.455, 95, 48, 58, (0.114, 0.114, 0.114))
add_box('running_gear', 'front_right_mud_tire_outer_lug_5', 735, 705, 770, 95, 48, 58, (0.114, 0.114, 0.114))
add_box('running_gear', 'front_right_mud_tire_outer_lug_6', 591.494, 705, 741.455, 95, 48, 58, (0.114, 0.114, 0.114))
add_box('running_gear', 'front_right_mud_tire_outer_lug_7', 469.835, 705, 660.165, 95, 48, 58, (0.114, 0.114, 0.114))
add_box('running_gear', 'front_right_mud_tire_outer_lug_8', 388.545, 705, 538.506, 95, 48, 58, (0.114, 0.114, 0.114))
add_box('running_gear', 'front_right_mud_tire_outer_lug_9', 360, 705, 395, 95, 48, 58, (0.114, 0.114, 0.114))
add_box('running_gear', 'front_right_mud_tire_outer_lug_10', 388.545, 705, 251.494, 95, 48, 58, (0.114, 0.114, 0.114))
add_box('running_gear', 'front_right_mud_tire_outer_lug_11', 469.835, 705, 129.835, 95, 48, 58, (0.114, 0.114, 0.114))
add_box('running_gear', 'front_right_mud_tire_outer_lug_12', 591.494, 705, 48.5452, 95, 48, 58, (0.114, 0.114, 0.114))
add_box('running_gear', 'front_right_mud_tire_outer_lug_13', 735, 705, 20, 95, 48, 58, (0.114, 0.114, 0.114))
add_box('running_gear', 'front_right_mud_tire_outer_lug_14', 878.506, 705, 48.5452, 95, 48, 58, (0.114, 0.114, 0.114))
add_box('running_gear', 'front_right_mud_tire_outer_lug_15', 1000.17, 705, 129.835, 95, 48, 58, (0.114, 0.114, 0.114))
add_box('running_gear', 'front_right_mud_tire_outer_lug_16', 1081.45, 705, 251.494, 95, 48, 58, (0.114, 0.114, 0.114))
add_box('running_gear', 'rear_left_mud_tire_outer_lug_1', 3395, -705, 395, 95, 48, 58, (0.114, 0.114, 0.114))
add_box('running_gear', 'rear_left_mud_tire_outer_lug_2', 3366.45, -705, 538.506, 95, 48, 58, (0.114, 0.114, 0.114))
add_box('running_gear', 'rear_left_mud_tire_outer_lug_3', 3285.17, -705, 660.165, 95, 48, 58, (0.114, 0.114, 0.114))
add_box('running_gear', 'rear_left_mud_tire_outer_lug_4', 3163.51, -705, 741.455, 95, 48, 58, (0.114, 0.114, 0.114))
add_box('running_gear', 'rear_left_mud_tire_outer_lug_5', 3020, -705, 770, 95, 48, 58, (0.114, 0.114, 0.114))
add_box('running_gear', 'rear_left_mud_tire_outer_lug_6', 2876.49, -705, 741.455, 95, 48, 58, (0.114, 0.114, 0.114))
add_box('running_gear', 'rear_left_mud_tire_outer_lug_7', 2754.83, -705, 660.165, 95, 48, 58, (0.114, 0.114, 0.114))
add_box('running_gear', 'rear_left_mud_tire_outer_lug_8', 2673.55, -705, 538.506, 95, 48, 58, (0.114, 0.114, 0.114))
add_box('running_gear', 'rear_left_mud_tire_outer_lug_9', 2645, -705, 395, 95, 48, 58, (0.114, 0.114, 0.114))
add_box('running_gear', 'rear_left_mud_tire_outer_lug_10', 2673.55, -705, 251.494, 95, 48, 58, (0.114, 0.114, 0.114))
add_box('running_gear', 'rear_left_mud_tire_outer_lug_11', 2754.83, -705, 129.835, 95, 48, 58, (0.114, 0.114, 0.114))
add_box('running_gear', 'rear_left_mud_tire_outer_lug_12', 2876.49, -705, 48.5452, 95, 48, 58, (0.114, 0.114, 0.114))
add_box('running_gear', 'rear_left_mud_tire_outer_lug_13', 3020, -705, 20, 95, 48, 58, (0.114, 0.114, 0.114))
add_box('running_gear', 'rear_left_mud_tire_outer_lug_14', 3163.51, -705, 48.5452, 95, 48, 58, (0.114, 0.114, 0.114))
add_box('running_gear', 'rear_left_mud_tire_outer_lug_15', 3285.17, -705, 129.835, 95, 48, 58, (0.114, 0.114, 0.114))
add_box('running_gear', 'rear_left_mud_tire_outer_lug_16', 3366.45, -705, 251.494, 95, 48, 58, (0.114, 0.114, 0.114))
add_box('running_gear', 'rear_right_mud_tire_outer_lug_1', 3395, 705, 395, 95, 48, 58, (0.114, 0.114, 0.114))
add_box('running_gear', 'rear_right_mud_tire_outer_lug_2', 3366.45, 705, 538.506, 95, 48, 58, (0.114, 0.114, 0.114))
add_box('running_gear', 'rear_right_mud_tire_outer_lug_3', 3285.17, 705, 660.165, 95, 48, 58, (0.114, 0.114, 0.114))
add_box('running_gear', 'rear_right_mud_tire_outer_lug_4', 3163.51, 705, 741.455, 95, 48, 58, (0.114, 0.114, 0.114))
add_box('running_gear', 'rear_right_mud_tire_outer_lug_5', 3020, 705, 770, 95, 48, 58, (0.114, 0.114, 0.114))
add_box('running_gear', 'rear_right_mud_tire_outer_lug_6', 2876.49, 705, 741.455, 95, 48, 58, (0.114, 0.114, 0.114))
add_box('running_gear', 'rear_right_mud_tire_outer_lug_7', 2754.83, 705, 660.165, 95, 48, 58, (0.114, 0.114, 0.114))
add_box('running_gear', 'rear_right_mud_tire_outer_lug_8', 2673.55, 705, 538.506, 95, 48, 58, (0.114, 0.114, 0.114))
add_box('running_gear', 'rear_right_mud_tire_outer_lug_9', 2645, 705, 395, 95, 48, 58, (0.114, 0.114, 0.114))
add_box('running_gear', 'rear_right_mud_tire_outer_lug_10', 2673.55, 705, 251.494, 95, 48, 58, (0.114, 0.114, 0.114))
add_box('running_gear', 'rear_right_mud_tire_outer_lug_11', 2754.83, 705, 129.835, 95, 48, 58, (0.114, 0.114, 0.114))
add_box('running_gear', 'rear_right_mud_tire_outer_lug_12', 2876.49, 705, 48.5452, 95, 48, 58, (0.114, 0.114, 0.114))
add_box('running_gear', 'rear_right_mud_tire_outer_lug_13', 3020, 705, 20, 95, 48, 58, (0.114, 0.114, 0.114))
add_box('running_gear', 'rear_right_mud_tire_outer_lug_14', 3163.51, 705, 48.5452, 95, 48, 58, (0.114, 0.114, 0.114))
add_box('running_gear', 'rear_right_mud_tire_outer_lug_15', 3285.17, 705, 129.835, 95, 48, 58, (0.114, 0.114, 0.114))
add_box('running_gear', 'rear_right_mud_tire_outer_lug_16', 3366.45, 705, 251.494, 95, 48, 58, (0.114, 0.114, 0.114))
add_cylinder('running_gear', 'front_left_shock_body', 920, -520, 620, 'z', 58, 460, (0.722, 0.722, 0.722))
add_cylinder('running_gear', 'front_right_shock_body', 920, 520, 620, 'z', 58, 460, (0.722, 0.722, 0.722))
add_cylinder('running_gear', 'front_left_hub_cap', 735, -840, 395, 'y', 220, 80, (0.722, 0.722, 0.722))
add_cylinder('running_gear', 'front_right_hub_cap', 735, 840, 395, 'y', 220, 80, (0.722, 0.722, 0.722))
add_cylinder('running_gear', 'rear_left_shock_body', 3205, -520, 620, 'z', 58, 460, (0.722, 0.722, 0.722))
add_cylinder('running_gear', 'rear_right_shock_body', 3205, 520, 620, 'z', 58, 460, (0.722, 0.722, 0.722))
add_cylinder('running_gear', 'rear_left_hub_cap', 3020, -840, 395, 'y', 220, 80, (0.722, 0.722, 0.722))
add_cylinder('running_gear', 'rear_right_hub_cap', 3020, 840, 395, 'y', 220, 80, (0.722, 0.722, 0.722))
add_box('body', 'floor_pan', 890, 0, 615, 2550, 1330, 55, (0.812, 0.776, 0.667))
add_box('body', 'left_rocker_sill', 1000, -720, 665, 2050, 95, 155, (0.812, 0.776, 0.667))
add_box('body', 'right_rocker_sill', 1000, 720, 665, 2050, 95, 155, (0.812, 0.776, 0.667))
add_box('body', 'left_rear_quarter_panel', 2140, -760, 725, 1270, 70, 610, (0.812, 0.776, 0.667))
add_box('body', 'right_rear_quarter_panel', 2140, 760, 725, 1270, 70, 610, (0.812, 0.776, 0.667))
add_box('body', 'tailgate_panel', 3400, 0, 720, 70, 1430, 650, (0.812, 0.776, 0.667))
add_box('body', 'firewall', 1135, 0, 690, 80, 1420, 780, (0.812, 0.776, 0.667))
add_box('body', 'cowl_top', 1085, 0, 1260, 190, 1460, 110, (0.812, 0.776, 0.667))
add_box('body', 'grille_panel', 170, 0, 790, 80, 1410, 520, (0.812, 0.776, 0.667))
add_box('front_detail', 'white_grille_surround', 125, 0, 795, 35, 1120, 365, (0.910, 0.910, 0.910))
add_box('front_detail', 'black_grille_mesh', 105, 0, 910, 30, 640, 155, (0.114, 0.114, 0.114))
add_cylinder('front_detail', 'left_headlamp', 92, -445, 985, 'x', 225, 38, (0.910, 0.910, 0.910))
add_cylinder('front_detail', 'right_headlamp', 92, 445, 985, 'x', 225, 38, (0.910, 0.910, 0.910))
add_cylinder('front_detail', 'left_indicator_lamp', 84, -720, 845, 'x', 105, 30, (0.722, 0.482, 0.333))
add_cylinder('front_detail', 'right_indicator_lamp', 84, 720, 845, 'x', 105, 30, (0.722, 0.482, 0.333))
add_cylinder('front_detail', 'left_fog_lamp', 25, -360, 620, 'x', 165, 36, (0.910, 0.910, 0.910))
add_cylinder('front_detail', 'right_fog_lamp', 25, 360, 620, 'x', 165, 36, (0.910, 0.910, 0.910))
add_box('body', 'hood_closed_reference', 230, 0, 1215, 920, 1390, 38, (0.812, 0.776, 0.667))
add_mesh('body', 'hood_crowned_closed_skin', [(135, -642, 1230), (135, 0, 1256), (135, 642, 1230), (1058, -642, 1296), (1058, 0, 1322), (1058, 642, 1296), (135, -642, 1210), (135, 0, 1236), (135, 642, 1210), (1058, -642, 1276), (1058, 0, 1302), (1058, 642, 1276)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.812, 0.776, 0.667))
add_mesh('body', 'hood_front_rolled_lip_surface', [(96, -610, 1204), (96, 610, 1204), (150, 610, 1218), (150, -610, 1218), (96, -610, 1248), (96, 610, 1248), (150, 610, 1254), (150, -610, 1254)], [(0, 1, 2, 3), (4, 7, 6, 5), (0, 4, 5, 1), (1, 5, 6, 2), (2, 6, 7, 3), (3, 7, 4, 0)], (0.616, 0.588, 0.494))
add_cylinder('body', 'hood_left_hinge_axis', 1030, -540, 1288, 'y', 28, 230, (0.722, 0.722, 0.722))
add_cylinder('body', 'hood_right_hinge_axis', 1030, 540, 1288, 'y', 28, 230, (0.722, 0.722, 0.722))
add_box('body', 'left_front_fender', 270, -720, 760, 860, 270, 260, (0.812, 0.776, 0.667))
add_box('body', 'right_front_fender', 270, 720, 760, 860, 270, 260, (0.812, 0.776, 0.667))
add_box('body', 'left_inner_fender', 290, -520, 800, 800, 70, 420, (0.812, 0.776, 0.667))
add_box('body', 'right_inner_fender', 290, 520, 800, 800, 70, 420, (0.812, 0.776, 0.667))
add_box('body', 'windshield_frame', 1155, 0, 1315, 80, 1480, 520, (0.812, 0.776, 0.667))
add_box('body', 'windshield_glass', 1160, 0, 1380, 35, 1300, 410, (0.435, 0.647, 0.722))
add_cylinder('body', 'windshield_left_wiper', 1110, -250, 1370, 'y', 24, 430, (0.114, 0.114, 0.114))
add_cylinder('body', 'windshield_right_wiper', 1110, 250, 1370, 'y', 24, 430, (0.114, 0.114, 0.114))
add_box('hard_top', 'white_hardtop_roof', 1210, 0, 1838, 2290, 1540, 58, (0.945, 0.933, 0.894))
add_mesh('hard_top', 'white_hardtop_crowned_roof_skin', [(1125, -760, 1886), (1125, 0, 1932), (1125, 760, 1886), (3440, -760, 1896), (3440, 0, 1942), (3440, 760, 1896), (1125, -760, 1860), (1125, 0, 1906), (1125, 760, 1860), (3440, -760, 1870), (3440, 0, 1916), (3440, 760, 1870)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.945, 0.933, 0.894))
add_box('hard_top', 'left_hardtop_side_panel', 1240, -790, 1320, 2200, 55, 590, (0.812, 0.776, 0.667))
add_box('hard_top', 'right_hardtop_side_panel', 1240, 790, 1320, 2200, 55, 590, (0.812, 0.776, 0.667))
add_box('hard_top', 'left_front_hardtop_window', 1420, -823, 1435, 500, 20, 320, (0.435, 0.647, 0.722))
add_box('hard_top', 'right_front_hardtop_window', 1420, 823, 1435, 500, 20, 320, (0.435, 0.647, 0.722))
add_mesh('hard_top', 'left_rear_hardtop_window', [(2495, -844, 1663), (2490.5, -844, 1691.43), (2477.43, -844, 1717.08), (2457.08, -844, 1737.43), (2431.43, -844, 1750.5), (2403, -844, 1755), (1948.57, -844, 1750.5), (1922.92, -844, 1737.43), (1902.57, -844, 1717.08), (1889.5, -844, 1691.43), (1885, -844, 1663), (1889.5, -844, 1498.57), (1902.57, -844, 1472.92), (1922.92, -844, 1452.57), (1948.57, -844, 1439.5), (1977, -844, 1435), (2431.43, -844, 1439.5), (2457.08, -844, 1452.57), (2477.43, -844, 1472.92), (2490.5, -844, 1498.57), (2495, -844, 1527), (2495, -820, 1663), (2490.5, -820, 1691.43), (2477.43, -820, 1717.08), (2457.08, -820, 1737.43), (2431.43, -820, 1750.5), (2403, -820, 1755), (1948.57, -820, 1750.5), (1922.92, -820, 1737.43), (1902.57, -820, 1717.08), (1889.5, -820, 1691.43), (1885, -820, 1663), (1889.5, -820, 1498.57), (1902.57, -820, 1472.92), (1922.92, -820, 1452.57), (1948.57, -820, 1439.5), (1977, -820, 1435), (2431.43, -820, 1439.5), (2457.08, -820, 1452.57), (2477.43, -820, 1472.92), (2490.5, -820, 1498.57), (2495, -820, 1527)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.435, 0.647, 0.722))
add_mesh('hard_top', 'right_rear_hardtop_window', [(2495, 820, 1663), (2490.5, 820, 1691.43), (2477.43, 820, 1717.08), (2457.08, 820, 1737.43), (2431.43, 820, 1750.5), (2403, 820, 1755), (1948.57, 820, 1750.5), (1922.92, 820, 1737.43), (1902.57, 820, 1717.08), (1889.5, 820, 1691.43), (1885, 820, 1663), (1889.5, 820, 1498.57), (1902.57, 820, 1472.92), (1922.92, 820, 1452.57), (1948.57, 820, 1439.5), (1977, 820, 1435), (2431.43, 820, 1439.5), (2457.08, 820, 1452.57), (2477.43, 820, 1472.92), (2490.5, 820, 1498.57), (2495, 820, 1527), (2495, 844, 1663), (2490.5, 844, 1691.43), (2477.43, 844, 1717.08), (2457.08, 844, 1737.43), (2431.43, 844, 1750.5), (2403, 844, 1755), (1948.57, 844, 1750.5), (1922.92, 844, 1737.43), (1902.57, 844, 1717.08), (1889.5, 844, 1691.43), (1885, 844, 1663), (1889.5, 844, 1498.57), (1902.57, 844, 1472.92), (1922.92, 844, 1452.57), (1948.57, 844, 1439.5), (1977, 844, 1435), (2431.43, 844, 1439.5), (2457.08, 844, 1452.57), (2477.43, 844, 1472.92), (2490.5, 844, 1498.57), (2495, 844, 1527)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.435, 0.647, 0.722))
add_box('hard_top', 'rear_hardtop_panel', 3440, 0, 1320, 55, 1540, 590, (0.812, 0.776, 0.667))
add_box('hard_top', 'roof_front_gutter', 1160, 0, 1810, 70, 1575, 46, (0.945, 0.933, 0.894))
add_box('hard_top', 'roof_left_gutter', 2250, -830, 1815, 2200, 58, 42, (0.945, 0.933, 0.894))
add_box('hard_top', 'roof_right_gutter', 2250, 830, 1815, 2200, 58, 42, (0.945, 0.933, 0.894))
add_box('body', 'left_door_open_reference', 1180, -910, 760, 800, 70, 850, (0.812, 0.776, 0.667))
add_box('body', 'right_door_closed_reference', 1180, 760, 760, 800, 70, 850, (0.812, 0.776, 0.667))
add_box('body', 'left_door_window_glass', 1280, -948, 1210, 520, 22, 345, (0.435, 0.647, 0.722))
add_box('body', 'right_door_window_glass', 1280, 798, 1210, 520, 22, 345, (0.435, 0.647, 0.722))
add_cylinder('body', 'left_upper_door_hinge', 1135, -955, 1180, 'z', 38, 145, (0.722, 0.722, 0.722))
add_cylinder('body', 'left_lower_door_hinge', 1135, -955, 850, 'z', 38, 145, (0.722, 0.722, 0.722))
add_cylinder('body', 'right_upper_door_hinge', 1135, 805, 1180, 'z', 38, 145, (0.722, 0.722, 0.722))
add_cylinder('body', 'right_lower_door_hinge', 1135, 805, 850, 'z', 38, 145, (0.722, 0.722, 0.722))
add_box('body', 'left_door_handle', 1575, -955, 1045, 160, 30, 40, (0.722, 0.722, 0.722))
add_box('body', 'right_door_handle', 1575, 805, 1045, 160, 30, 40, (0.722, 0.722, 0.722))
add_box('engine_bay', 'engine_block', 460, 0, 720, 520, 420, 430, (0.247, 0.259, 0.271))
add_box('engine_bay', 'valve_cover', 510, 0, 1080, 460, 180, 70, (0.722, 0.722, 0.722))
add_box('engine_bay', 'radiator', 235, 0, 820, 75, 980, 520, (0.247, 0.259, 0.271))
add_box('engine_bay', 'air_filter', 760, -235, 1120, 210, 210, 150, (0.247, 0.259, 0.271))
add_box('engine_bay', 'battery_tray_reference', 600, 430, 760, 330, 220, 220, (0.910, 0.910, 0.910))
add_cylinder('engine_bay', 'inline_six_intake_stack_1', 470, -165, 1160, 'z', 46, 180, (0.722, 0.722, 0.722))
add_cylinder('engine_bay', 'inline_six_intake_stack_2', 470, -99, 1160, 'z', 46, 180, (0.722, 0.722, 0.722))
add_cylinder('engine_bay', 'inline_six_intake_stack_3', 470, -33, 1160, 'z', 46, 180, (0.722, 0.722, 0.722))
add_cylinder('engine_bay', 'inline_six_intake_stack_4', 470, 33, 1160, 'z', 46, 180, (0.722, 0.722, 0.722))
add_cylinder('engine_bay', 'inline_six_intake_stack_5', 470, 99, 1160, 'z', 46, 180, (0.722, 0.722, 0.722))
add_cylinder('engine_bay', 'inline_six_intake_stack_6', 470, 165, 1160, 'z', 46, 180, (0.722, 0.722, 0.722))
add_cylinder('engine_bay', 'upper_radiator_hose', 330, -185, 1110, 'x', 72, 430, (0.114, 0.114, 0.114))
add_cylinder('engine_bay', 'exhaust_downpipe_reference', 615, 255, 845, 'z', 82, 460, (0.722, 0.722, 0.722))
add_box('interior', 'dashboard', 1235, 0, 1080, 120, 1320, 220, (0.722, 0.482, 0.333))
add_box('interior', 'steering_column', 1135, 420, 935, 590, 60, 60, (0.722, 0.722, 0.722))
add_cylinder('interior', 'steering_wheel', 1240, 420, 1210, 'x', 380, 32, (0.114, 0.114, 0.114))
add_cylinder('interior', 'steering_wheel_hub', 1230, 420, 1210, 'x', 135, 55, (0.722, 0.722, 0.722))
add_cylinder('interior', 'dashboard_gauge_1', 1222, 560, 1175, 'x', 72, 24, (0.910, 0.910, 0.910))
add_cylinder('interior', 'dashboard_gauge_2', 1222, 470, 1175, 'x', 72, 24, (0.910, 0.910, 0.910))
add_cylinder('interior', 'dashboard_gauge_3', 1222, 380, 1175, 'x', 72, 24, (0.910, 0.910, 0.910))
add_cylinder('interior', 'dashboard_gauge_4', 1222, 290, 1175, 'x', 72, 24, (0.910, 0.910, 0.910))
add_cylinder('interior', 'transfer_case_lever', 1580, -120, 820, 'z', 36, 285, (0.722, 0.722, 0.722))
add_cylinder('interior', 'gearshift_lever', 1500, -35, 820, 'z', 38, 330, (0.722, 0.722, 0.722))
add_box('interior', 'front_left_seat_base', 1660, -310, 700, 420, 410, 130, (0.722, 0.482, 0.333))
add_box('interior', 'front_left_seat_back', 1850, -310, 820, 95, 410, 620, (0.722, 0.482, 0.333))
add_cylinder('interior', 'front_left_headrest', 1905, -310, 1435, 'y', 150, 300, (0.722, 0.482, 0.333))
add_box('interior', 'front_right_seat_base', 1660, 310, 700, 420, 410, 130, (0.722, 0.482, 0.333))
add_box('interior', 'front_right_seat_back', 1850, 310, 820, 95, 410, 620, (0.722, 0.482, 0.333))
add_cylinder('interior', 'front_right_headrest', 1905, 310, 1435, 'y', 150, 300, (0.722, 0.482, 0.333))
add_box('interior', 'rear_bench_base', 2510, 0, 720, 610, 1080, 135, (0.722, 0.482, 0.333))
add_box('interior', 'rear_bench_back', 2920, 0, 840, 105, 1080, 560, (0.722, 0.482, 0.333))
add_cylinder('interior', 'rear_bench_left_headrest', 2975, -350, 1390, 'y', 140, 270, (0.722, 0.482, 0.333))
add_cylinder('interior', 'rear_bench_right_headrest', 2975, 350, 1390, 'y', 140, 270, (0.722, 0.482, 0.333))
add_mesh('body', 'windshield_raked_glass_surface', [(1110, -602, 1378), (1110, 602, 1378), (1148, 602, 1378), (1148, -602, 1378), (1110, -602, 1722), (1110, 602, 1722), (1148, 602, 1700), (1148, -602, 1700)], [(0, 1, 2, 3), (4, 7, 6, 5), (0, 4, 5, 1), (1, 5, 6, 2), (2, 6, 7, 3), (3, 7, 4, 0)], (0.435, 0.647, 0.722))
add_mesh('front_detail', 'front_grille_inset_rounded_surround_surface', [(56, -585, 802), (56, 585, 802), (106, 585, 820), (106, -585, 820), (56, -585, 1125), (56, 585, 1125), (106, 585, 1100), (106, -585, 1100)], [(0, 1, 2, 3), (4, 7, 6, 5), (0, 4, 5, 1), (1, 5, 6, 2), (2, 6, 7, 3), (3, 7, 4, 0)], (0.910, 0.910, 0.910))
add_mesh('chassis', 'front_bumper_swept_main_face', [(-18, -760, 484), (-18, 760, 484), (92, 760, 520), (92, -760, 520), (-18, -760, 608), (-18, 760, 608), (92, 760, 620), (92, -760, 620)], [(0, 1, 2, 3), (4, 7, 6, 5), (0, 4, 5, 1), (1, 5, 6, 2), (2, 6, 7, 3), (3, 7, 4, 0)], (0.067, 0.075, 0.082))
add_mesh('chassis', 'rear_bumper_swept_main_face', [(3638, -730, 492), (3638, 730, 492), (3750, 730, 520), (3750, -730, 520), (3638, -730, 604), (3638, 730, 604), (3750, 730, 612), (3750, -730, 612)], [(0, 1, 2, 3), (4, 7, 6, 5), (0, 4, 5, 1), (1, 5, 6, 2), (2, 6, 7, 3), (3, 7, 4, 0)], (0.067, 0.075, 0.082))
add_mesh('hard_top', 'front_roof_header_overhang_skin', [(1092, -786, 1808), (1092, 0, 1834), (1092, 786, 1808), (1208, -786, 1852), (1208, 0, 1878), (1208, 786, 1852), (1092, -786, 1792), (1092, 0, 1818), (1092, 786, 1792), (1208, -786, 1836), (1208, 0, 1862), (1208, 786, 1836)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.945, 0.933, 0.894))
add_mesh('hard_top', 'rear_roof_overhang_skin', [(3360, -776, 1862), (3360, 0, 1890), (3360, 776, 1862), (3508, -776, 1848), (3508, 0, 1876), (3508, 776, 1848), (3360, -776, 1844), (3360, 0, 1872), (3360, 776, 1844), (3508, -776, 1830), (3508, 0, 1858), (3508, 776, 1830)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.945, 0.933, 0.894))
add_mesh('hard_top', 'rear_barn_door_left_subtle_crown', [(3484, -690, 920), (3484, -354, 938), (3484, -18, 920), (3534, -690, 924), (3534, -354, 942), (3534, -18, 924), (3484, -690, 904), (3484, -354, 922), (3484, -18, 904), (3534, -690, 908), (3534, -354, 926), (3534, -18, 908)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.812, 0.776, 0.667))
add_mesh('hard_top', 'rear_barn_door_right_subtle_crown', [(3484, 18, 920), (3484, 354, 938), (3484, 690, 920), (3534, 18, 924), (3534, 354, 942), (3534, 690, 924), (3484, 18, 904), (3484, 354, 922), (3484, 690, 904), (3534, 18, 908), (3534, 354, 926), (3534, 690, 908)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.812, 0.776, 0.667))
add_mesh('body', 'left_front_fender_sloped_outer_skin', [(118, -846, 706), (118, -646, 706), (1035, -646, 744), (1035, -846, 744), (118, -846, 1048), (118, -646, 1048), (1035, -646, 1242), (1035, -846, 1242)], [(0, 1, 2, 3), (4, 7, 6, 5), (0, 4, 5, 1), (1, 5, 6, 2), (2, 6, 7, 3), (3, 7, 4, 0)], (0.812, 0.776, 0.667))
add_mesh('chassis', 'left_front_bumper_swept_return', [(24, -846, 500), (24, -720, 500), (128, -720, 548), (128, -846, 548), (24, -846, 610), (24, -720, 610), (128, -720, 620), (128, -846, 620)], [(0, 1, 2, 3), (4, 7, 6, 5), (0, 4, 5, 1), (1, 5, 6, 2), (2, 6, 7, 3), (3, 7, 4, 0)], (0.067, 0.075, 0.082))
add_mesh('chassis', 'left_rear_bumper_swept_return', [(3628, -812, 502), (3628, -695, 502), (3735, -695, 540), (3735, -812, 540), (3628, -812, 604), (3628, -695, 604), (3735, -695, 612), (3735, -812, 612)], [(0, 1, 2, 3), (4, 7, 6, 5), (0, 4, 5, 1), (1, 5, 6, 2), (2, 6, 7, 3), (3, 7, 4, 0)], (0.067, 0.075, 0.082))
add_mesh('body', 'left_front_fender_rolled_upper_crown', [(155, -754, 1062), (155, -560, 1062), (1015, -560, 1238), (1015, -754, 1238), (155, -754, 1110), (155, -560, 1110), (1015, -560, 1268), (1015, -754, 1268)], [(0, 1, 2, 3), (4, 7, 6, 5), (0, 4, 5, 1), (1, 5, 6, 2), (2, 6, 7, 3), (3, 7, 4, 0)], (0.894, 0.863, 0.780))
add_mesh('body', 'left_cowl_side_blend_surface', [(960, -815, 1116), (960, -660, 1116), (1165, -660, 1214), (1165, -815, 1214), (960, -815, 1340), (960, -660, 1340), (1165, -660, 1410), (1165, -815, 1410)], [(0, 1, 2, 3), (4, 7, 6, 5), (0, 4, 5, 1), (1, 5, 6, 2), (2, 6, 7, 3), (3, 7, 4, 0)], (0.812, 0.776, 0.667))
add_mesh('body', 'left_door_outer_skin_tapered_surface', [(1128, -824, 748), (1128, -734, 748), (1938, -734, 748), (1938, -824, 748), (1128, -824, 1270), (1128, -734, 1270), (1938, -734, 1308), (1938, -824, 1308)], [(0, 1, 2, 3), (4, 7, 6, 5), (0, 4, 5, 1), (1, 5, 6, 2), (2, 6, 7, 3), (3, 7, 4, 0)], (0.812, 0.776, 0.667))
add_mesh('body', 'left_rear_quarter_waist_tapered_surface', [(1942, -830, 724), (1942, -730, 724), (3385, -730, 746), (3385, -830, 746), (1942, -830, 1305), (1942, -730, 1305), (3385, -730, 1278), (3385, -830, 1278)], [(0, 1, 2, 3), (4, 7, 6, 5), (0, 4, 5, 1), (1, 5, 6, 2), (2, 6, 7, 3), (3, 7, 4, 0)], (0.812, 0.776, 0.667))
add_mesh('hard_top', 'left_hardtop_side_tapered_upper_skin', [(1212, -820, 1308), (1212, -748, 1308), (3425, -748, 1300), (3425, -820, 1300), (1212, -820, 1790), (1212, -748, 1790), (3425, -748, 1782), (3425, -820, 1782)], [(0, 1, 2, 3), (4, 7, 6, 5), (0, 4, 5, 1), (1, 5, 6, 2), (2, 6, 7, 3), (3, 7, 4, 0)], (0.812, 0.776, 0.667))
add_mesh('hard_top', 'left_hardtop_lower_side_roll_surface', [(1225, -812, 1260), (1225, -742, 1260), (3415, -742, 1258), (3415, -812, 1258), (1225, -812, 1345), (1225, -742, 1345), (3415, -742, 1332), (3415, -812, 1332)], [(0, 1, 2, 3), (4, 7, 6, 5), (0, 4, 5, 1), (1, 5, 6, 2), (2, 6, 7, 3), (3, 7, 4, 0)], (0.616, 0.588, 0.494))
add_mesh('hard_top', 'left_hardtop_rear_corner_radius_facet', [(3365, -806, 1300), (3365, -650, 1300), (3470, -650, 1308), (3470, -806, 1308), (3365, -806, 1780), (3365, -650, 1780), (3470, -650, 1762), (3470, -806, 1762)], [(0, 1, 2, 3), (4, 7, 6, 5), (0, 4, 5, 1), (1, 5, 6, 2), (2, 6, 7, 3), (3, 7, 4, 0)], (0.616, 0.588, 0.494))
add_mesh('body', 'left_front_outer_arch_rounded_skin_facet_1', [(1015.74, -846, 700), (1015.74, -734, 700), (1087.74, -734, 700), (1087.74, -846, 700), (1015.74, -846, 625.5), (1015.74, -734, 625.5), (1087.74, -734, 625.5), (1087.74, -846, 625.5)], [(0, 1, 2, 3), (4, 7, 6, 5), (0, 4, 5, 1), (1, 5, 6, 2), (2, 6, 7, 3), (3, 7, 4, 0)], (0.812, 0.776, 0.667))
add_mesh('body', 'left_front_outer_arch_rounded_skin_facet_2', [(935.998, -846, 700), (935.998, -734, 700), (1008, -734, 700), (1008, -846, 700), (935.998, -846, 723.974), (935.998, -734, 723.974), (1008, -734, 723.974), (1008, -846, 723.974)], [(0, 1, 2, 3), (4, 7, 6, 5), (0, 4, 5, 1), (1, 5, 6, 2), (2, 6, 7, 3), (3, 7, 4, 0)], (0.812, 0.776, 0.667))
add_mesh('body', 'left_front_outer_arch_rounded_skin_facet_3', [(829.728, -846, 740.986), (829.728, -734, 740.986), (901.728, -734, 740.986), (901.728, -846, 740.986), (829.728, -846, 792.986), (829.728, -734, 792.986), (901.728, -734, 792.986), (901.728, -846, 792.986)], [(0, 1, 2, 3), (4, 7, 6, 5), (0, 4, 5, 1), (1, 5, 6, 2), (2, 6, 7, 3), (3, 7, 4, 0)], (0.812, 0.776, 0.667))
add_mesh('body', 'left_front_outer_arch_rounded_skin_facet_4', [(707.334, -846, 773.781), (707.334, -734, 773.781), (779.334, -734, 773.781), (779.334, -846, 773.781), (707.334, -846, 825.781), (707.334, -734, 825.781), (779.334, -734, 825.781), (779.334, -846, 825.781)], [(0, 1, 2, 3), (4, 7, 6, 5), (0, 4, 5, 1), (1, 5, 6, 2), (2, 6, 7, 3), (3, 7, 4, 0)], (0.812, 0.776, 0.667))
add_mesh('body', 'left_front_outer_arch_rounded_skin_facet_5', [(580.796, -846, 767.15), (580.796, -734, 767.15), (652.796, -734, 767.15), (652.796, -846, 767.15), (580.796, -846, 819.15), (580.796, -734, 819.15), (652.796, -734, 819.15), (652.796, -846, 819.15)], [(0, 1, 2, 3), (4, 7, 6, 5), (0, 4, 5, 1), (1, 5, 6, 2), (2, 6, 7, 3), (3, 7, 4, 0)], (0.812, 0.776, 0.667))
add_mesh('body', 'left_front_outer_arch_rounded_skin_facet_6', [(462.5, -846, 721.74), (462.5, -734, 721.74), (534.5, -734, 721.74), (534.5, -846, 721.74), (462.5, -846, 773.74), (462.5, -734, 773.74), (534.5, -734, 773.74), (534.5, -846, 773.74)], [(0, 1, 2, 3), (4, 7, 6, 5), (0, 4, 5, 1), (1, 5, 6, 2), (2, 6, 7, 3), (3, 7, 4, 0)], (0.812, 0.776, 0.667))
add_mesh('body', 'left_front_outer_arch_rounded_skin_facet_7', [(364.026, -846, 700), (364.026, -734, 700), (436.026, -734, 700), (436.026, -846, 700), (364.026, -846, 693.998), (364.026, -734, 693.998), (436.026, -734, 693.998), (436.026, -846, 693.998)], [(0, 1, 2, 3), (4, 7, 6, 5), (0, 4, 5, 1), (1, 5, 6, 2), (2, 6, 7, 3), (3, 7, 4, 0)], (0.812, 0.776, 0.667))
add_mesh('body', 'left_rear_outer_arch_rounded_skin_facet_1', [(3287.75, -846, 688), (3287.75, -734, 688), (3359.75, -734, 688), (3359.75, -846, 688), (3287.75, -846, 618), (3287.75, -734, 618), (3359.75, -734, 618), (3359.75, -846, 618)], [(0, 1, 2, 3), (4, 7, 6, 5), (0, 4, 5, 1), (1, 5, 6, 2), (2, 6, 7, 3), (3, 7, 4, 0)], (0.812, 0.776, 0.667))
add_mesh('body', 'left_rear_outer_arch_rounded_skin_facet_2', [(3210.96, -846, 688), (3210.96, -734, 688), (3282.96, -734, 688), (3282.96, -846, 688), (3210.96, -846, 712.826), (3210.96, -734, 712.826), (3282.96, -734, 712.826), (3282.96, -846, 712.826)], [(0, 1, 2, 3), (4, 7, 6, 5), (0, 4, 5, 1), (1, 5, 6, 2), (2, 6, 7, 3), (3, 7, 4, 0)], (0.812, 0.776, 0.667))
add_mesh('body', 'left_rear_outer_arch_rounded_skin_facet_3', [(3108.63, -846, 727.283), (3108.63, -734, 727.283), (3180.63, -734, 727.283), (3180.63, -846, 727.283), (3108.63, -846, 779.283), (3108.63, -734, 779.283), (3180.63, -734, 779.283), (3180.63, -846, 779.283)], [(0, 1, 2, 3), (4, 7, 6, 5), (0, 4, 5, 1), (1, 5, 6, 2), (2, 6, 7, 3), (3, 7, 4, 0)], (0.812, 0.776, 0.667))
add_mesh('body', 'left_rear_outer_arch_rounded_skin_facet_4', [(2990.77, -846, 758.864), (2990.77, -734, 758.864), (3062.77, -734, 758.864), (3062.77, -846, 758.864), (2990.77, -846, 810.864), (2990.77, -734, 810.864), (3062.77, -734, 810.864), (3062.77, -846, 810.864)], [(0, 1, 2, 3), (4, 7, 6, 5), (0, 4, 5, 1), (1, 5, 6, 2), (2, 6, 7, 3), (3, 7, 4, 0)], (0.812, 0.776, 0.667))
add_mesh('body', 'left_rear_outer_arch_rounded_skin_facet_5', [(2868.91, -846, 752.478), (2868.91, -734, 752.478), (2940.91, -734, 752.478), (2940.91, -846, 752.478), (2868.91, -846, 804.478), (2868.91, -734, 804.478), (2940.91, -734, 804.478), (2940.91, -846, 804.478)], [(0, 1, 2, 3), (4, 7, 6, 5), (0, 4, 5, 1), (1, 5, 6, 2), (2, 6, 7, 3), (3, 7, 4, 0)], (0.812, 0.776, 0.667))
add_mesh('body', 'left_rear_outer_arch_rounded_skin_facet_6', [(2755, -846, 708.75), (2755, -734, 708.75), (2827, -734, 708.75), (2827, -846, 708.75), (2755, -846, 760.75), (2755, -734, 760.75), (2827, -734, 760.75), (2827, -846, 760.75)], [(0, 1, 2, 3), (4, 7, 6, 5), (0, 4, 5, 1), (1, 5, 6, 2), (2, 6, 7, 3), (3, 7, 4, 0)], (0.812, 0.776, 0.667))
add_mesh('body', 'left_rear_outer_arch_rounded_skin_facet_7', [(2660.17, -846, 688), (2660.17, -734, 688), (2732.17, -734, 688), (2732.17, -846, 688), (2660.17, -846, 683.961), (2660.17, -734, 683.961), (2732.17, -734, 683.961), (2732.17, -846, 683.961)], [(0, 1, 2, 3), (4, 7, 6, 5), (0, 4, 5, 1), (1, 5, 6, 2), (2, 6, 7, 3), (3, 7, 4, 0)], (0.812, 0.776, 0.667))
add_mesh('body', 'right_front_fender_sloped_outer_skin', [(118, 646, 706), (118, 846, 706), (1035, 846, 744), (1035, 646, 744), (118, 646, 1048), (118, 846, 1048), (1035, 846, 1242), (1035, 646, 1242)], [(0, 1, 2, 3), (4, 7, 6, 5), (0, 4, 5, 1), (1, 5, 6, 2), (2, 6, 7, 3), (3, 7, 4, 0)], (0.812, 0.776, 0.667))
add_mesh('chassis', 'right_front_bumper_swept_return', [(24, 720, 500), (24, 846, 500), (128, 846, 548), (128, 720, 548), (24, 720, 610), (24, 846, 610), (128, 846, 620), (128, 720, 620)], [(0, 1, 2, 3), (4, 7, 6, 5), (0, 4, 5, 1), (1, 5, 6, 2), (2, 6, 7, 3), (3, 7, 4, 0)], (0.067, 0.075, 0.082))
add_mesh('chassis', 'right_rear_bumper_swept_return', [(3628, 695, 502), (3628, 812, 502), (3735, 812, 540), (3735, 695, 540), (3628, 695, 604), (3628, 812, 604), (3735, 812, 612), (3735, 695, 612)], [(0, 1, 2, 3), (4, 7, 6, 5), (0, 4, 5, 1), (1, 5, 6, 2), (2, 6, 7, 3), (3, 7, 4, 0)], (0.067, 0.075, 0.082))
add_mesh('body', 'right_front_fender_rolled_upper_crown', [(155, 560, 1062), (155, 754, 1062), (1015, 754, 1238), (1015, 560, 1238), (155, 560, 1110), (155, 754, 1110), (1015, 754, 1268), (1015, 560, 1268)], [(0, 1, 2, 3), (4, 7, 6, 5), (0, 4, 5, 1), (1, 5, 6, 2), (2, 6, 7, 3), (3, 7, 4, 0)], (0.894, 0.863, 0.780))
add_mesh('body', 'right_cowl_side_blend_surface', [(960, 660, 1116), (960, 815, 1116), (1165, 815, 1214), (1165, 660, 1214), (960, 660, 1340), (960, 815, 1340), (1165, 815, 1410), (1165, 660, 1410)], [(0, 1, 2, 3), (4, 7, 6, 5), (0, 4, 5, 1), (1, 5, 6, 2), (2, 6, 7, 3), (3, 7, 4, 0)], (0.812, 0.776, 0.667))
add_mesh('body', 'right_door_outer_skin_tapered_surface', [(1128, 734, 748), (1128, 824, 748), (1938, 824, 748), (1938, 734, 748), (1128, 734, 1270), (1128, 824, 1270), (1938, 824, 1308), (1938, 734, 1308)], [(0, 1, 2, 3), (4, 7, 6, 5), (0, 4, 5, 1), (1, 5, 6, 2), (2, 6, 7, 3), (3, 7, 4, 0)], (0.812, 0.776, 0.667))
add_mesh('body', 'right_rear_quarter_waist_tapered_surface', [(1942, 730, 724), (1942, 830, 724), (3385, 830, 746), (3385, 730, 746), (1942, 730, 1305), (1942, 830, 1305), (3385, 830, 1278), (3385, 730, 1278)], [(0, 1, 2, 3), (4, 7, 6, 5), (0, 4, 5, 1), (1, 5, 6, 2), (2, 6, 7, 3), (3, 7, 4, 0)], (0.812, 0.776, 0.667))
add_mesh('hard_top', 'right_hardtop_side_tapered_upper_skin', [(1212, 748, 1308), (1212, 820, 1308), (3425, 820, 1300), (3425, 748, 1300), (1212, 748, 1790), (1212, 820, 1790), (3425, 820, 1782), (3425, 748, 1782)], [(0, 1, 2, 3), (4, 7, 6, 5), (0, 4, 5, 1), (1, 5, 6, 2), (2, 6, 7, 3), (3, 7, 4, 0)], (0.812, 0.776, 0.667))
add_mesh('hard_top', 'right_hardtop_lower_side_roll_surface', [(1225, 742, 1260), (1225, 812, 1260), (3415, 812, 1258), (3415, 742, 1258), (1225, 742, 1345), (1225, 812, 1345), (3415, 812, 1332), (3415, 742, 1332)], [(0, 1, 2, 3), (4, 7, 6, 5), (0, 4, 5, 1), (1, 5, 6, 2), (2, 6, 7, 3), (3, 7, 4, 0)], (0.616, 0.588, 0.494))
add_mesh('hard_top', 'right_hardtop_rear_corner_radius_facet', [(3365, 650, 1300), (3365, 806, 1300), (3470, 806, 1308), (3470, 650, 1308), (3365, 650, 1780), (3365, 806, 1780), (3470, 806, 1762), (3470, 650, 1762)], [(0, 1, 2, 3), (4, 7, 6, 5), (0, 4, 5, 1), (1, 5, 6, 2), (2, 6, 7, 3), (3, 7, 4, 0)], (0.616, 0.588, 0.494))
add_mesh('body', 'right_front_outer_arch_rounded_skin_facet_1', [(1015.74, 734, 700), (1015.74, 846, 700), (1087.74, 846, 700), (1087.74, 734, 700), (1015.74, 734, 625.5), (1015.74, 846, 625.5), (1087.74, 846, 625.5), (1087.74, 734, 625.5)], [(0, 1, 2, 3), (4, 7, 6, 5), (0, 4, 5, 1), (1, 5, 6, 2), (2, 6, 7, 3), (3, 7, 4, 0)], (0.812, 0.776, 0.667))
add_mesh('body', 'right_front_outer_arch_rounded_skin_facet_2', [(935.998, 734, 700), (935.998, 846, 700), (1008, 846, 700), (1008, 734, 700), (935.998, 734, 723.974), (935.998, 846, 723.974), (1008, 846, 723.974), (1008, 734, 723.974)], [(0, 1, 2, 3), (4, 7, 6, 5), (0, 4, 5, 1), (1, 5, 6, 2), (2, 6, 7, 3), (3, 7, 4, 0)], (0.812, 0.776, 0.667))
add_mesh('body', 'right_front_outer_arch_rounded_skin_facet_3', [(829.728, 734, 740.986), (829.728, 846, 740.986), (901.728, 846, 740.986), (901.728, 734, 740.986), (829.728, 734, 792.986), (829.728, 846, 792.986), (901.728, 846, 792.986), (901.728, 734, 792.986)], [(0, 1, 2, 3), (4, 7, 6, 5), (0, 4, 5, 1), (1, 5, 6, 2), (2, 6, 7, 3), (3, 7, 4, 0)], (0.812, 0.776, 0.667))
add_mesh('body', 'right_front_outer_arch_rounded_skin_facet_4', [(707.334, 734, 773.781), (707.334, 846, 773.781), (779.334, 846, 773.781), (779.334, 734, 773.781), (707.334, 734, 825.781), (707.334, 846, 825.781), (779.334, 846, 825.781), (779.334, 734, 825.781)], [(0, 1, 2, 3), (4, 7, 6, 5), (0, 4, 5, 1), (1, 5, 6, 2), (2, 6, 7, 3), (3, 7, 4, 0)], (0.812, 0.776, 0.667))
add_mesh('body', 'right_front_outer_arch_rounded_skin_facet_5', [(580.796, 734, 767.15), (580.796, 846, 767.15), (652.796, 846, 767.15), (652.796, 734, 767.15), (580.796, 734, 819.15), (580.796, 846, 819.15), (652.796, 846, 819.15), (652.796, 734, 819.15)], [(0, 1, 2, 3), (4, 7, 6, 5), (0, 4, 5, 1), (1, 5, 6, 2), (2, 6, 7, 3), (3, 7, 4, 0)], (0.812, 0.776, 0.667))
add_mesh('body', 'right_front_outer_arch_rounded_skin_facet_6', [(462.5, 734, 721.74), (462.5, 846, 721.74), (534.5, 846, 721.74), (534.5, 734, 721.74), (462.5, 734, 773.74), (462.5, 846, 773.74), (534.5, 846, 773.74), (534.5, 734, 773.74)], [(0, 1, 2, 3), (4, 7, 6, 5), (0, 4, 5, 1), (1, 5, 6, 2), (2, 6, 7, 3), (3, 7, 4, 0)], (0.812, 0.776, 0.667))
add_mesh('body', 'right_front_outer_arch_rounded_skin_facet_7', [(364.026, 734, 700), (364.026, 846, 700), (436.026, 846, 700), (436.026, 734, 700), (364.026, 734, 693.998), (364.026, 846, 693.998), (436.026, 846, 693.998), (436.026, 734, 693.998)], [(0, 1, 2, 3), (4, 7, 6, 5), (0, 4, 5, 1), (1, 5, 6, 2), (2, 6, 7, 3), (3, 7, 4, 0)], (0.812, 0.776, 0.667))
add_mesh('body', 'right_rear_outer_arch_rounded_skin_facet_1', [(3287.75, 734, 688), (3287.75, 846, 688), (3359.75, 846, 688), (3359.75, 734, 688), (3287.75, 734, 618), (3287.75, 846, 618), (3359.75, 846, 618), (3359.75, 734, 618)], [(0, 1, 2, 3), (4, 7, 6, 5), (0, 4, 5, 1), (1, 5, 6, 2), (2, 6, 7, 3), (3, 7, 4, 0)], (0.812, 0.776, 0.667))
add_mesh('body', 'right_rear_outer_arch_rounded_skin_facet_2', [(3210.96, 734, 688), (3210.96, 846, 688), (3282.96, 846, 688), (3282.96, 734, 688), (3210.96, 734, 712.826), (3210.96, 846, 712.826), (3282.96, 846, 712.826), (3282.96, 734, 712.826)], [(0, 1, 2, 3), (4, 7, 6, 5), (0, 4, 5, 1), (1, 5, 6, 2), (2, 6, 7, 3), (3, 7, 4, 0)], (0.812, 0.776, 0.667))
add_mesh('body', 'right_rear_outer_arch_rounded_skin_facet_3', [(3108.63, 734, 727.283), (3108.63, 846, 727.283), (3180.63, 846, 727.283), (3180.63, 734, 727.283), (3108.63, 734, 779.283), (3108.63, 846, 779.283), (3180.63, 846, 779.283), (3180.63, 734, 779.283)], [(0, 1, 2, 3), (4, 7, 6, 5), (0, 4, 5, 1), (1, 5, 6, 2), (2, 6, 7, 3), (3, 7, 4, 0)], (0.812, 0.776, 0.667))
add_mesh('body', 'right_rear_outer_arch_rounded_skin_facet_4', [(2990.77, 734, 758.864), (2990.77, 846, 758.864), (3062.77, 846, 758.864), (3062.77, 734, 758.864), (2990.77, 734, 810.864), (2990.77, 846, 810.864), (3062.77, 846, 810.864), (3062.77, 734, 810.864)], [(0, 1, 2, 3), (4, 7, 6, 5), (0, 4, 5, 1), (1, 5, 6, 2), (2, 6, 7, 3), (3, 7, 4, 0)], (0.812, 0.776, 0.667))
add_mesh('body', 'right_rear_outer_arch_rounded_skin_facet_5', [(2868.91, 734, 752.478), (2868.91, 846, 752.478), (2940.91, 846, 752.478), (2940.91, 734, 752.478), (2868.91, 734, 804.478), (2868.91, 846, 804.478), (2940.91, 846, 804.478), (2940.91, 734, 804.478)], [(0, 1, 2, 3), (4, 7, 6, 5), (0, 4, 5, 1), (1, 5, 6, 2), (2, 6, 7, 3), (3, 7, 4, 0)], (0.812, 0.776, 0.667))
add_mesh('body', 'right_rear_outer_arch_rounded_skin_facet_6', [(2755, 734, 708.75), (2755, 846, 708.75), (2827, 846, 708.75), (2827, 734, 708.75), (2755, 734, 760.75), (2755, 846, 760.75), (2827, 846, 760.75), (2827, 734, 760.75)], [(0, 1, 2, 3), (4, 7, 6, 5), (0, 4, 5, 1), (1, 5, 6, 2), (2, 6, 7, 3), (3, 7, 4, 0)], (0.812, 0.776, 0.667))
add_mesh('body', 'right_rear_outer_arch_rounded_skin_facet_7', [(2660.17, 734, 688), (2660.17, 846, 688), (2732.17, 846, 688), (2732.17, 734, 688), (2660.17, 734, 683.961), (2660.17, 846, 683.961), (2732.17, 846, 683.961), (2732.17, 734, 683.961)], [(0, 1, 2, 3), (4, 7, 6, 5), (0, 4, 5, 1), (1, 5, 6, 2), (2, 6, 7, 3), (3, 7, 4, 0)], (0.812, 0.776, 0.667))
add_box('chassis', 'left_front_frame_horn_top_plate', 120, -390, 555, 500, 95, 24, (0.176, 0.188, 0.200))
add_box('chassis', 'left_front_frame_horn_side_web', 120, -448, 440, 500, 18, 150, (0.176, 0.188, 0.200))
add_box('chassis', 'left_rear_frame_horn_top_plate', 3230, -390, 555, 420, 95, 24, (0.176, 0.188, 0.200))
add_box('chassis', 'left_rear_frame_horn_side_web', 3230, -448, 440, 420, 18, 145, (0.176, 0.188, 0.200))
add_box('chassis', 'left_body_mount_outrigger_1', 740, -525, 525, 280, 70, 55, (0.176, 0.188, 0.200))
add_cylinder('chassis', 'left_body_mount_rubber_biscuit_1', 965, -615, 610, 'z', 118, 42, (0.114, 0.114, 0.114))
add_cylinder('chassis', 'left_body_mount_center_bolt_1', 965, -615, 632, 'z', 30, 70, (0.722, 0.722, 0.722))
add_box('chassis', 'left_body_mount_outrigger_2', 1135, -525, 525, 280, 70, 55, (0.176, 0.188, 0.200))
add_cylinder('chassis', 'left_body_mount_rubber_biscuit_2', 1360, -615, 610, 'z', 118, 42, (0.114, 0.114, 0.114))
add_cylinder('chassis', 'left_body_mount_center_bolt_2', 1360, -615, 632, 'z', 30, 70, (0.722, 0.722, 0.722))
add_box('chassis', 'left_body_mount_outrigger_3', 1610, -525, 525, 280, 70, 55, (0.176, 0.188, 0.200))
add_cylinder('chassis', 'left_body_mount_rubber_biscuit_3', 1835, -615, 610, 'z', 118, 42, (0.114, 0.114, 0.114))
add_cylinder('chassis', 'left_body_mount_center_bolt_3', 1835, -615, 632, 'z', 30, 70, (0.722, 0.722, 0.722))
add_box('chassis', 'left_body_mount_outrigger_4', 2250, -525, 525, 280, 70, 55, (0.176, 0.188, 0.200))
add_cylinder('chassis', 'left_body_mount_rubber_biscuit_4', 2475, -615, 610, 'z', 118, 42, (0.114, 0.114, 0.114))
add_cylinder('chassis', 'left_body_mount_center_bolt_4', 2475, -615, 632, 'z', 30, 70, (0.722, 0.722, 0.722))
add_box('chassis', 'left_body_mount_outrigger_5', 2920, -525, 525, 280, 70, 55, (0.176, 0.188, 0.200))
add_cylinder('chassis', 'left_body_mount_rubber_biscuit_5', 3145, -615, 610, 'z', 118, 42, (0.114, 0.114, 0.114))
add_cylinder('chassis', 'left_body_mount_center_bolt_5', 3145, -615, 632, 'z', 30, 70, (0.722, 0.722, 0.722))
add_box('chassis', 'left_front_fixed_spring_hanger_outer_plate', 210, -475, 360, 105, 28, 180, (0.176, 0.188, 0.200))
add_box('chassis', 'left_front_fixed_spring_hanger_inner_plate', 210, -390, 360, 105, 28, 180, (0.176, 0.188, 0.200))
add_cylinder('chassis', 'left_front_fixed_spring_pin', 262, -432.5, 430, 'y', 42, 130, (0.722, 0.722, 0.722))
add_box('chassis', 'left_front_shackle_spring_hanger_outer_plate', 1280, -475, 360, 105, 28, 180, (0.176, 0.188, 0.200))
add_box('chassis', 'left_front_shackle_spring_hanger_inner_plate', 1280, -390, 360, 105, 28, 180, (0.176, 0.188, 0.200))
add_cylinder('chassis', 'left_front_shackle_spring_pin', 1332, -432.5, 430, 'y', 42, 130, (0.722, 0.722, 0.722))
add_box('chassis', 'left_rear_fixed_spring_hanger_outer_plate', 2495, -475, 360, 105, 28, 180, (0.176, 0.188, 0.200))
add_box('chassis', 'left_rear_fixed_spring_hanger_inner_plate', 2495, -390, 360, 105, 28, 180, (0.176, 0.188, 0.200))
add_cylinder('chassis', 'left_rear_fixed_spring_pin', 2547, -432.5, 430, 'y', 42, 130, (0.722, 0.722, 0.722))
add_box('chassis', 'left_rear_shackle_spring_hanger_outer_plate', 3565, -475, 360, 105, 28, 180, (0.176, 0.188, 0.200))
add_box('chassis', 'left_rear_shackle_spring_hanger_inner_plate', 3565, -390, 360, 105, 28, 180, (0.176, 0.188, 0.200))
add_cylinder('chassis', 'left_rear_shackle_spring_pin', 3617, -432.5, 430, 'y', 42, 130, (0.722, 0.722, 0.722))
add_box('chassis', 'left_crossmember_1_gusset_front', 898, -390, 465, 38, 230, 90, (0.176, 0.188, 0.200))
add_box('chassis', 'left_crossmember_1_gusset_rear', 1106, -390, 465, 38, 230, 90, (0.176, 0.188, 0.200))
add_box('chassis', 'left_crossmember_2_gusset_front', 1578, -390, 465, 38, 230, 90, (0.176, 0.188, 0.200))
add_box('chassis', 'left_crossmember_2_gusset_rear', 1786, -390, 465, 38, 230, 90, (0.176, 0.188, 0.200))
add_box('chassis', 'left_crossmember_3_gusset_front', 2338, -390, 465, 38, 230, 90, (0.176, 0.188, 0.200))
add_box('chassis', 'left_crossmember_3_gusset_rear', 2546, -390, 465, 38, 230, 90, (0.176, 0.188, 0.200))
add_box('running_gear', 'left_front_upper_shock_mount', 945, -575, 875, 115, 110, 135, (0.176, 0.188, 0.200))
add_box('running_gear', 'left_rear_upper_shock_mount', 3185, -575, 875, 115, 110, 135, (0.176, 0.188, 0.200))
add_cylinder('running_gear', 'left_front_shock_piston_rod', 920, -520, 850, 'z', 24, 280, (0.722, 0.722, 0.722))
add_cylinder('running_gear', 'left_rear_shock_piston_rod', 3205, -520, 850, 'z', 24, 280, (0.722, 0.722, 0.722))
add_box('running_gear', 'left_front_bump_stop', 640, -495, 540, 115, 80, 72, (0.114, 0.114, 0.114))
add_box('running_gear', 'left_rear_bump_stop', 2925, -495, 540, 115, 80, 72, (0.114, 0.114, 0.114))
add_box('chassis', 'right_front_frame_horn_top_plate', 120, 390, 555, 500, 95, 24, (0.176, 0.188, 0.200))
add_box('chassis', 'right_front_frame_horn_side_web', 120, 448, 440, 500, 18, 150, (0.176, 0.188, 0.200))
add_box('chassis', 'right_rear_frame_horn_top_plate', 3230, 390, 555, 420, 95, 24, (0.176, 0.188, 0.200))
add_box('chassis', 'right_rear_frame_horn_side_web', 3230, 448, 440, 420, 18, 145, (0.176, 0.188, 0.200))
add_box('chassis', 'right_body_mount_outrigger_1', 740, 525, 525, 280, 70, 55, (0.176, 0.188, 0.200))
add_cylinder('chassis', 'right_body_mount_rubber_biscuit_1', 965, 615, 610, 'z', 118, 42, (0.114, 0.114, 0.114))
add_cylinder('chassis', 'right_body_mount_center_bolt_1', 965, 615, 632, 'z', 30, 70, (0.722, 0.722, 0.722))
add_box('chassis', 'right_body_mount_outrigger_2', 1135, 525, 525, 280, 70, 55, (0.176, 0.188, 0.200))
add_cylinder('chassis', 'right_body_mount_rubber_biscuit_2', 1360, 615, 610, 'z', 118, 42, (0.114, 0.114, 0.114))
add_cylinder('chassis', 'right_body_mount_center_bolt_2', 1360, 615, 632, 'z', 30, 70, (0.722, 0.722, 0.722))
add_box('chassis', 'right_body_mount_outrigger_3', 1610, 525, 525, 280, 70, 55, (0.176, 0.188, 0.200))
add_cylinder('chassis', 'right_body_mount_rubber_biscuit_3', 1835, 615, 610, 'z', 118, 42, (0.114, 0.114, 0.114))
add_cylinder('chassis', 'right_body_mount_center_bolt_3', 1835, 615, 632, 'z', 30, 70, (0.722, 0.722, 0.722))
add_box('chassis', 'right_body_mount_outrigger_4', 2250, 525, 525, 280, 70, 55, (0.176, 0.188, 0.200))
add_cylinder('chassis', 'right_body_mount_rubber_biscuit_4', 2475, 615, 610, 'z', 118, 42, (0.114, 0.114, 0.114))
add_cylinder('chassis', 'right_body_mount_center_bolt_4', 2475, 615, 632, 'z', 30, 70, (0.722, 0.722, 0.722))
add_box('chassis', 'right_body_mount_outrigger_5', 2920, 525, 525, 280, 70, 55, (0.176, 0.188, 0.200))
add_cylinder('chassis', 'right_body_mount_rubber_biscuit_5', 3145, 615, 610, 'z', 118, 42, (0.114, 0.114, 0.114))
add_cylinder('chassis', 'right_body_mount_center_bolt_5', 3145, 615, 632, 'z', 30, 70, (0.722, 0.722, 0.722))
add_box('chassis', 'right_front_fixed_spring_hanger_outer_plate', 210, 475, 360, 105, 28, 180, (0.176, 0.188, 0.200))
add_box('chassis', 'right_front_fixed_spring_hanger_inner_plate', 210, 390, 360, 105, 28, 180, (0.176, 0.188, 0.200))
add_cylinder('chassis', 'right_front_fixed_spring_pin', 262, 432.5, 430, 'y', 42, 130, (0.722, 0.722, 0.722))
add_box('chassis', 'right_front_shackle_spring_hanger_outer_plate', 1280, 475, 360, 105, 28, 180, (0.176, 0.188, 0.200))
add_box('chassis', 'right_front_shackle_spring_hanger_inner_plate', 1280, 390, 360, 105, 28, 180, (0.176, 0.188, 0.200))
add_cylinder('chassis', 'right_front_shackle_spring_pin', 1332, 432.5, 430, 'y', 42, 130, (0.722, 0.722, 0.722))
add_box('chassis', 'right_rear_fixed_spring_hanger_outer_plate', 2495, 475, 360, 105, 28, 180, (0.176, 0.188, 0.200))
add_box('chassis', 'right_rear_fixed_spring_hanger_inner_plate', 2495, 390, 360, 105, 28, 180, (0.176, 0.188, 0.200))
add_cylinder('chassis', 'right_rear_fixed_spring_pin', 2547, 432.5, 430, 'y', 42, 130, (0.722, 0.722, 0.722))
add_box('chassis', 'right_rear_shackle_spring_hanger_outer_plate', 3565, 475, 360, 105, 28, 180, (0.176, 0.188, 0.200))
add_box('chassis', 'right_rear_shackle_spring_hanger_inner_plate', 3565, 390, 360, 105, 28, 180, (0.176, 0.188, 0.200))
add_cylinder('chassis', 'right_rear_shackle_spring_pin', 3617, 432.5, 430, 'y', 42, 130, (0.722, 0.722, 0.722))
add_box('chassis', 'right_crossmember_1_gusset_front', 898, 390, 465, 38, 230, 90, (0.176, 0.188, 0.200))
add_box('chassis', 'right_crossmember_1_gusset_rear', 1106, 390, 465, 38, 230, 90, (0.176, 0.188, 0.200))
add_box('chassis', 'right_crossmember_2_gusset_front', 1578, 390, 465, 38, 230, 90, (0.176, 0.188, 0.200))
add_box('chassis', 'right_crossmember_2_gusset_rear', 1786, 390, 465, 38, 230, 90, (0.176, 0.188, 0.200))
add_box('chassis', 'right_crossmember_3_gusset_front', 2338, 390, 465, 38, 230, 90, (0.176, 0.188, 0.200))
add_box('chassis', 'right_crossmember_3_gusset_rear', 2546, 390, 465, 38, 230, 90, (0.176, 0.188, 0.200))
add_box('running_gear', 'right_front_upper_shock_mount', 945, 575, 875, 115, 110, 135, (0.176, 0.188, 0.200))
add_box('running_gear', 'right_rear_upper_shock_mount', 3185, 575, 875, 115, 110, 135, (0.176, 0.188, 0.200))
add_cylinder('running_gear', 'right_front_shock_piston_rod', 920, 520, 850, 'z', 24, 280, (0.722, 0.722, 0.722))
add_cylinder('running_gear', 'right_rear_shock_piston_rod', 3205, 520, 850, 'z', 24, 280, (0.722, 0.722, 0.722))
add_box('running_gear', 'right_front_bump_stop', 640, 495, 540, 115, 80, 72, (0.114, 0.114, 0.114))
add_box('running_gear', 'right_rear_bump_stop', 2925, 495, 540, 115, 80, 72, (0.114, 0.114, 0.114))
add_box('chassis', 'transfer_case_crossmember', 1710, 0, 500, 260, 940, 120, (0.176, 0.188, 0.200))
add_box('chassis', 'skid_plate_transfer_case', 1600, 0, 315, 520, 620, 42, (0.722, 0.722, 0.722))
add_box('running_gear', 'transfer_case', 1640, 0, 575, 410, 360, 265, (0.247, 0.259, 0.271))
add_box('running_gear', 'gearbox_tail_housing', 1325, 0, 610, 430, 300, 260, (0.247, 0.259, 0.271))
add_cylinder('running_gear', 'front_prop_shaft', 1120, 0, 465, 'x', 82, 900, (0.722, 0.722, 0.722))
add_cylinder('running_gear', 'rear_prop_shaft', 2180, 0, 465, 'x', 82, 1360, (0.722, 0.722, 0.722))
add_cylinder('running_gear', 'front_diff_pumpkin', 735, 0, 420, 'y', 360, 300, (0.722, 0.722, 0.722))
add_cylinder('running_gear', 'rear_diff_pumpkin', 3020, 0, 420, 'y', 380, 320, (0.722, 0.722, 0.722))
add_cylinder('running_gear', 'front_pinion_nose', 920, 0, 430, 'x', 145, 310, (0.722, 0.722, 0.722))
add_cylinder('running_gear', 'rear_pinion_nose', 2780, 0, 430, 'x', 145, 310, (0.722, 0.722, 0.722))
add_box('chassis', 'right_hand_drive_steering_box', 535, 515, 610, 245, 175, 230, (0.722, 0.722, 0.722))
add_box('chassis', 'steering_box_right_frame_mount_plate', 500, 445, 600, 295, 28, 260, (0.176, 0.188, 0.200))
add_cylinder('running_gear', 'pitman_arm_right_hand_drive', 675, 555, 565, 'z', 62, 250, (0.722, 0.722, 0.722))
add_cylinder('running_gear', 'front_drag_link_right_hand_drive', 875, 555, 505, 'x', 34, 620, (0.722, 0.722, 0.722))
add_cylinder('running_gear', 'front_tie_rod', 735, 0, 505, 'y', 32, 1420, (0.722, 0.722, 0.722))
add_cylinder('running_gear', 'steering_damper', 905, 350, 480, 'x', 58, 520, (0.722, 0.722, 0.722))
add_box('running_gear', 'front_left_steering_knuckle_arm', 855, -690, 475, 150, 58, 60, (0.722, 0.722, 0.722))
add_box('running_gear', 'front_right_steering_knuckle_arm', 855, 690, 475, 150, 58, 60, (0.722, 0.722, 0.722))
add_cylinder('running_gear', 'front_left_brake_backing_plate', 735, -750, 395, 'y', 365, 55, (0.722, 0.722, 0.722))
add_cylinder('running_gear', 'front_right_brake_backing_plate', 735, 750, 395, 'y', 365, 55, (0.722, 0.722, 0.722))
add_box('running_gear', 'front_left_leaf_spring_layer_1', 215, -430, 305, 935, 78, 14, (0.133, 0.133, 0.133))
add_box('running_gear', 'front_left_leaf_spring_layer_2', 215, -430, 323, 820, 78, 14, (0.133, 0.133, 0.133))
add_box('running_gear', 'front_left_leaf_spring_layer_3', 215, -430, 341, 705, 78, 14, (0.133, 0.133, 0.133))
add_cylinder('running_gear', 'front_left_u_bolt_1', 670, -430, 405, 'z', 24, 210, (0.722, 0.722, 0.722))
add_cylinder('running_gear', 'front_left_u_bolt_2', 800, -430, 405, 'z', 24, 210, (0.722, 0.722, 0.722))
add_cylinder('running_gear', 'front_left_fixed_spring_eye_bushing', 262, -430, 430, 'y', 92, 96, (0.114, 0.114, 0.114))
add_cylinder('running_gear', 'front_left_fixed_spring_eye_inner_sleeve', 262, -430, 430, 'y', 38, 132, (0.722, 0.722, 0.722))
add_cylinder('chassis', 'left_front_fixed_hanger_cross_sleeve', 262, -432.5, 430, 'y', 44, 152, (0.722, 0.722, 0.722))
add_cylinder('chassis', 'left_front_fixed_hanger_pin_bolt', 262, -432.5, 430, 'y', 30, 190, (0.769, 0.604, 0.239))
add_box('chassis', 'left_front_fixed_hanger_outer_bolt_head', 244, -553, 412, 36, 18, 36, (0.769, 0.604, 0.239))
add_box('chassis', 'left_front_fixed_hanger_inner_nut', 244, -312, 412, 36, 18, 36, (0.769, 0.604, 0.239))
add_mesh('running_gear', 'front_left_fixed_eye_leaf_wrap_upper', [(272.78, -465, 438.932), (251.22, -465, 421.068), (309.22, -465, 351.068), (330.78, -465, 368.932), (272.78, -395, 438.932), (251.22, -395, 421.068), (309.22, -395, 351.068), (330.78, -395, 368.932)], [(0, 1, 2, 3), (4, 7, 6, 5), (0, 4, 5, 1), (1, 5, 6, 2), (2, 6, 7, 3), (3, 7, 4, 0)], (0.133, 0.133, 0.133))
add_mesh('running_gear', 'front_left_fixed_eye_leaf_wrap_lower', [(268.803, -463, 420.644), (255.197, -463, 403.356), (363.197, -463, 318.356), (376.803, -463, 335.644), (268.803, -397, 420.644), (255.197, -397, 403.356), (363.197, -397, 318.356), (376.803, -397, 335.644)], [(0, 1, 2, 3), (4, 7, 6, 5), (0, 4, 5, 1), (1, 5, 6, 2), (2, 6, 7, 3), (3, 7, 4, 0)], (0.133, 0.133, 0.133))
add_cylinder('chassis', 'left_front_shackle_upper_frame_bushing', 1332, -432.5, 430, 'y', 86, 126, (0.114, 0.114, 0.114))
add_cylinder('chassis', 'left_front_shackle_upper_sleeve', 1332, -432.5, 430, 'y', 36, 152, (0.722, 0.722, 0.722))
add_cylinder('running_gear', 'front_left_shackle_lower_spring_eye_bushing', 1261, -430, 356, 'y', 92, 96, (0.114, 0.114, 0.114))
add_cylinder('running_gear', 'front_left_shackle_lower_spring_eye_sleeve', 1261, -430, 356, 'y', 38, 132, (0.722, 0.722, 0.722))
add_mesh('running_gear', 'front_left_shackle_outer_link_plate', [(1352.93, -516, 409.922), (1311.07, -516, 450.078), (1240.07, -516, 376.078), (1281.93, -516, 335.922), (1352.93, -498, 409.922), (1311.07, -498, 450.078), (1240.07, -498, 376.078), (1281.93, -498, 335.922)], [(0, 1, 2, 3), (4, 7, 6, 5), (0, 4, 5, 1), (1, 5, 6, 2), (2, 6, 7, 3), (3, 7, 4, 0)], (0.722, 0.722, 0.722))
add_mesh('running_gear', 'front_left_shackle_inner_link_plate', [(1352.93, -369, 409.922), (1311.07, -369, 450.078), (1240.07, -369, 376.078), (1281.93, -369, 335.922), (1352.93, -351, 409.922), (1311.07, -351, 450.078), (1240.07, -351, 376.078), (1281.93, -351, 335.922)], [(0, 1, 2, 3), (4, 7, 6, 5), (0, 4, 5, 1), (1, 5, 6, 2), (2, 6, 7, 3), (3, 7, 4, 0)], (0.722, 0.722, 0.722))
add_cylinder('running_gear', 'front_left_shackle_upper_pin_bolt', 1332, -432.5, 430, 'y', 30, 190, (0.769, 0.604, 0.239))
add_cylinder('running_gear', 'front_left_shackle_lower_pin_bolt', 1261, -430, 356, 'y', 30, 168, (0.769, 0.604, 0.239))
add_mesh('running_gear', 'front_left_shackle_eye_leaf_wrap_upper', [(1260.78, -465, 342.002), (1261.22, -465, 369.998), (1135.22, -465, 371.998), (1134.78, -465, 344.002), (1260.78, -395, 342.002), (1261.22, -395, 369.998), (1135.22, -395, 371.998), (1134.78, -395, 344.002)], [(0, 1, 2, 3), (4, 7, 6, 5), (0, 4, 5, 1), (1, 5, 6, 2), (2, 6, 7, 3), (3, 7, 4, 0)], (0.133, 0.133, 0.133))
add_mesh('running_gear', 'front_left_shackle_eye_leaf_wrap_lower', [(1261.74, -463, 327.025), (1260.26, -463, 348.975), (1081.26, -463, 336.975), (1082.74, -463, 315.025), (1261.74, -397, 327.025), (1260.26, -397, 348.975), (1081.26, -397, 336.975), (1082.74, -397, 315.025)], [(0, 1, 2, 3), (4, 7, 6, 5), (0, 4, 5, 1), (1, 5, 6, 2), (2, 6, 7, 3), (3, 7, 4, 0)], (0.133, 0.133, 0.133))
add_box('running_gear', 'front_left_leaf_pack_rebound_clip_1', 403, -430, 300, 44, 98, 72, (0.722, 0.722, 0.722))
add_cylinder('running_gear', 'front_left_leaf_pack_rebound_clip_1_bolt', 425, -430, 352, 'y', 16, 112, (0.769, 0.604, 0.239))
add_box('running_gear', 'front_left_leaf_pack_rebound_clip_2', 1028, -430, 300, 44, 98, 72, (0.722, 0.722, 0.722))
add_cylinder('running_gear', 'front_left_leaf_pack_rebound_clip_2_bolt', 1050, -430, 352, 'y', 16, 112, (0.769, 0.604, 0.239))
add_cylinder('running_gear', 'front_left_spring_center_bolt', 735, -430, 338, 'z', 18, 88, (0.769, 0.604, 0.239))
add_box('running_gear', 'front_left_axle_spring_perch_welded_saddle', 653, -430, 352, 164, 126, 38, (0.722, 0.722, 0.722))
add_box('running_gear', 'front_left_spring_perch_lower_clamp_plate', 609, -430, 290, 252, 146, 34, (0.722, 0.722, 0.722))
add_box('running_gear', 'front_left_axle_tube_contact_pad', 643, -430, 452, 184, 132, 24, (0.722, 0.722, 0.722))
add_box('running_gear', 'front_left_u_bolt_1_top_crown', 647, -430, 490, 36, 118, 24, (0.722, 0.722, 0.722))
add_cylinder('running_gear', 'front_left_u_bolt_1_leg_1', 665, -472, 394, 'z', 18, 226, (0.722, 0.722, 0.722))
add_cylinder('running_gear', 'front_left_u_bolt_1_leg_1_lower_nut', 665, -472, 276, 'z', 32, 24, (0.769, 0.604, 0.239))
add_cylinder('running_gear', 'front_left_u_bolt_1_leg_2', 665, -388, 394, 'z', 18, 226, (0.722, 0.722, 0.722))
add_cylinder('running_gear', 'front_left_u_bolt_1_leg_2_lower_nut', 665, -388, 276, 'z', 32, 24, (0.769, 0.604, 0.239))
add_box('running_gear', 'front_left_u_bolt_2_top_crown', 787, -430, 490, 36, 118, 24, (0.722, 0.722, 0.722))
add_cylinder('running_gear', 'front_left_u_bolt_2_leg_1', 805, -472, 394, 'z', 18, 226, (0.722, 0.722, 0.722))
add_cylinder('running_gear', 'front_left_u_bolt_2_leg_1_lower_nut', 805, -472, 276, 'z', 32, 24, (0.769, 0.604, 0.239))
add_cylinder('running_gear', 'front_left_u_bolt_2_leg_2', 805, -388, 394, 'z', 18, 226, (0.722, 0.722, 0.722))
add_cylinder('running_gear', 'front_left_u_bolt_2_leg_2_lower_nut', 805, -388, 276, 'z', 32, 24, (0.769, 0.604, 0.239))
add_box('running_gear', 'front_left_shock_lower_mount_inner_tab', 853, -484, 349, 48, 18, 92, (0.722, 0.722, 0.722))
add_box('running_gear', 'front_left_shock_lower_mount_outer_tab', 853, -556, 349, 48, 18, 92, (0.722, 0.722, 0.722))
add_cylinder('running_gear', 'front_left_shock_lower_pin', 877, -520, 395, 'y', 30, 126, (0.769, 0.604, 0.239))
add_cylinder('running_gear', 'front_left_shock_lower_eye_bushing', 877, -520, 395, 'y', 72, 82, (0.114, 0.114, 0.114))
add_box('running_gear', 'front_left_shock_upper_tower_gusset_front', 901, -520, 765, 38, 118, 110, (0.176, 0.188, 0.200))
add_box('running_gear', 'front_left_shock_upper_tower_gusset_rear', 987, -520, 765, 38, 118, 110, (0.176, 0.188, 0.200))
add_cylinder('running_gear', 'front_left_shock_upper_pin', 945, -520, 855, 'y', 30, 146, (0.769, 0.604, 0.239))
add_cylinder('running_gear', 'front_left_shock_upper_eye_bushing', 945, -520, 855, 'y', 72, 86, (0.114, 0.114, 0.114))
add_mesh('running_gear', 'front_left_shock_centerline_connection_path', [(864.14, -541, 396.901), (889.86, -541, 393.099), (957.86, -541, 853.099), (932.14, -541, 856.901), (864.14, -499, 396.901), (889.86, -499, 393.099), (957.86, -499, 853.099), (932.14, -499, 856.901)], [(0, 1, 2, 3), (4, 7, 6, 5), (0, 4, 5, 1), (1, 5, 6, 2), (2, 6, 7, 3), (3, 7, 4, 0)], (0.486, 0.435, 0.796))
add_box('running_gear', 'front_left_bump_stop_axle_strike_pad', 590, -495, 476, 138, 105, 22, (0.722, 0.722, 0.722))
add_cylinder('datum', 'front_left_fixed_hanger_pin_center_datum', 262, -430, 430, 'y', 12, 170, (0.486, 0.435, 0.796))
add_cylinder('datum', 'front_left_shackle_upper_pin_center_datum', 1332, -430, 430, 'y', 12, 170, (0.486, 0.435, 0.796))
add_cylinder('datum', 'front_left_shackle_lower_pin_center_datum', 1261, -430, 356, 'y', 12, 152, (0.486, 0.435, 0.796))
add_box('running_gear', 'front_right_leaf_spring_layer_1', 215, 430, 305, 935, 78, 14, (0.133, 0.133, 0.133))
add_box('running_gear', 'front_right_leaf_spring_layer_2', 215, 430, 323, 820, 78, 14, (0.133, 0.133, 0.133))
add_box('running_gear', 'front_right_leaf_spring_layer_3', 215, 430, 341, 705, 78, 14, (0.133, 0.133, 0.133))
add_cylinder('running_gear', 'front_right_u_bolt_1', 670, 430, 405, 'z', 24, 210, (0.722, 0.722, 0.722))
add_cylinder('running_gear', 'front_right_u_bolt_2', 800, 430, 405, 'z', 24, 210, (0.722, 0.722, 0.722))
add_cylinder('running_gear', 'front_right_fixed_spring_eye_bushing', 262, 430, 430, 'y', 92, 96, (0.114, 0.114, 0.114))
add_cylinder('running_gear', 'front_right_fixed_spring_eye_inner_sleeve', 262, 430, 430, 'y', 38, 132, (0.722, 0.722, 0.722))
add_cylinder('chassis', 'right_front_fixed_hanger_cross_sleeve', 262, 432.5, 430, 'y', 44, 152, (0.722, 0.722, 0.722))
add_cylinder('chassis', 'right_front_fixed_hanger_pin_bolt', 262, 432.5, 430, 'y', 30, 190, (0.769, 0.604, 0.239))
add_box('chassis', 'right_front_fixed_hanger_outer_bolt_head', 244, 553, 412, 36, 18, 36, (0.769, 0.604, 0.239))
add_box('chassis', 'right_front_fixed_hanger_inner_nut', 244, 312, 412, 36, 18, 36, (0.769, 0.604, 0.239))
add_mesh('running_gear', 'front_right_fixed_eye_leaf_wrap_upper', [(272.78, 395, 438.932), (251.22, 395, 421.068), (309.22, 395, 351.068), (330.78, 395, 368.932), (272.78, 465, 438.932), (251.22, 465, 421.068), (309.22, 465, 351.068), (330.78, 465, 368.932)], [(0, 1, 2, 3), (4, 7, 6, 5), (0, 4, 5, 1), (1, 5, 6, 2), (2, 6, 7, 3), (3, 7, 4, 0)], (0.133, 0.133, 0.133))
add_mesh('running_gear', 'front_right_fixed_eye_leaf_wrap_lower', [(268.803, 397, 420.644), (255.197, 397, 403.356), (363.197, 397, 318.356), (376.803, 397, 335.644), (268.803, 463, 420.644), (255.197, 463, 403.356), (363.197, 463, 318.356), (376.803, 463, 335.644)], [(0, 1, 2, 3), (4, 7, 6, 5), (0, 4, 5, 1), (1, 5, 6, 2), (2, 6, 7, 3), (3, 7, 4, 0)], (0.133, 0.133, 0.133))
add_cylinder('chassis', 'right_front_shackle_upper_frame_bushing', 1332, 432.5, 430, 'y', 86, 126, (0.114, 0.114, 0.114))
add_cylinder('chassis', 'right_front_shackle_upper_sleeve', 1332, 432.5, 430, 'y', 36, 152, (0.722, 0.722, 0.722))
add_cylinder('running_gear', 'front_right_shackle_lower_spring_eye_bushing', 1261, 430, 356, 'y', 92, 96, (0.114, 0.114, 0.114))
add_cylinder('running_gear', 'front_right_shackle_lower_spring_eye_sleeve', 1261, 430, 356, 'y', 38, 132, (0.722, 0.722, 0.722))
add_mesh('running_gear', 'front_right_shackle_outer_link_plate', [(1352.93, 498, 409.922), (1311.07, 498, 450.078), (1240.07, 498, 376.078), (1281.93, 498, 335.922), (1352.93, 516, 409.922), (1311.07, 516, 450.078), (1240.07, 516, 376.078), (1281.93, 516, 335.922)], [(0, 1, 2, 3), (4, 7, 6, 5), (0, 4, 5, 1), (1, 5, 6, 2), (2, 6, 7, 3), (3, 7, 4, 0)], (0.722, 0.722, 0.722))
add_mesh('running_gear', 'front_right_shackle_inner_link_plate', [(1352.93, 351, 409.922), (1311.07, 351, 450.078), (1240.07, 351, 376.078), (1281.93, 351, 335.922), (1352.93, 369, 409.922), (1311.07, 369, 450.078), (1240.07, 369, 376.078), (1281.93, 369, 335.922)], [(0, 1, 2, 3), (4, 7, 6, 5), (0, 4, 5, 1), (1, 5, 6, 2), (2, 6, 7, 3), (3, 7, 4, 0)], (0.722, 0.722, 0.722))
add_cylinder('running_gear', 'front_right_shackle_upper_pin_bolt', 1332, 432.5, 430, 'y', 30, 190, (0.769, 0.604, 0.239))
add_cylinder('running_gear', 'front_right_shackle_lower_pin_bolt', 1261, 430, 356, 'y', 30, 168, (0.769, 0.604, 0.239))
add_mesh('running_gear', 'front_right_shackle_eye_leaf_wrap_upper', [(1260.78, 395, 342.002), (1261.22, 395, 369.998), (1135.22, 395, 371.998), (1134.78, 395, 344.002), (1260.78, 465, 342.002), (1261.22, 465, 369.998), (1135.22, 465, 371.998), (1134.78, 465, 344.002)], [(0, 1, 2, 3), (4, 7, 6, 5), (0, 4, 5, 1), (1, 5, 6, 2), (2, 6, 7, 3), (3, 7, 4, 0)], (0.133, 0.133, 0.133))
add_mesh('running_gear', 'front_right_shackle_eye_leaf_wrap_lower', [(1261.74, 397, 327.025), (1260.26, 397, 348.975), (1081.26, 397, 336.975), (1082.74, 397, 315.025), (1261.74, 463, 327.025), (1260.26, 463, 348.975), (1081.26, 463, 336.975), (1082.74, 463, 315.025)], [(0, 1, 2, 3), (4, 7, 6, 5), (0, 4, 5, 1), (1, 5, 6, 2), (2, 6, 7, 3), (3, 7, 4, 0)], (0.133, 0.133, 0.133))
add_box('running_gear', 'front_right_leaf_pack_rebound_clip_1', 403, 430, 300, 44, 98, 72, (0.722, 0.722, 0.722))
add_cylinder('running_gear', 'front_right_leaf_pack_rebound_clip_1_bolt', 425, 430, 352, 'y', 16, 112, (0.769, 0.604, 0.239))
add_box('running_gear', 'front_right_leaf_pack_rebound_clip_2', 1028, 430, 300, 44, 98, 72, (0.722, 0.722, 0.722))
add_cylinder('running_gear', 'front_right_leaf_pack_rebound_clip_2_bolt', 1050, 430, 352, 'y', 16, 112, (0.769, 0.604, 0.239))
add_cylinder('running_gear', 'front_right_spring_center_bolt', 735, 430, 338, 'z', 18, 88, (0.769, 0.604, 0.239))
add_box('running_gear', 'front_right_axle_spring_perch_welded_saddle', 653, 430, 352, 164, 126, 38, (0.722, 0.722, 0.722))
add_box('running_gear', 'front_right_spring_perch_lower_clamp_plate', 609, 430, 290, 252, 146, 34, (0.722, 0.722, 0.722))
add_box('running_gear', 'front_right_axle_tube_contact_pad', 643, 430, 452, 184, 132, 24, (0.722, 0.722, 0.722))
add_box('running_gear', 'front_right_u_bolt_1_top_crown', 647, 430, 490, 36, 118, 24, (0.722, 0.722, 0.722))
add_cylinder('running_gear', 'front_right_u_bolt_1_leg_1', 665, 388, 394, 'z', 18, 226, (0.722, 0.722, 0.722))
add_cylinder('running_gear', 'front_right_u_bolt_1_leg_1_lower_nut', 665, 388, 276, 'z', 32, 24, (0.769, 0.604, 0.239))
add_cylinder('running_gear', 'front_right_u_bolt_1_leg_2', 665, 472, 394, 'z', 18, 226, (0.722, 0.722, 0.722))
add_cylinder('running_gear', 'front_right_u_bolt_1_leg_2_lower_nut', 665, 472, 276, 'z', 32, 24, (0.769, 0.604, 0.239))
add_box('running_gear', 'front_right_u_bolt_2_top_crown', 787, 430, 490, 36, 118, 24, (0.722, 0.722, 0.722))
add_cylinder('running_gear', 'front_right_u_bolt_2_leg_1', 805, 388, 394, 'z', 18, 226, (0.722, 0.722, 0.722))
add_cylinder('running_gear', 'front_right_u_bolt_2_leg_1_lower_nut', 805, 388, 276, 'z', 32, 24, (0.769, 0.604, 0.239))
add_cylinder('running_gear', 'front_right_u_bolt_2_leg_2', 805, 472, 394, 'z', 18, 226, (0.722, 0.722, 0.722))
add_cylinder('running_gear', 'front_right_u_bolt_2_leg_2_lower_nut', 805, 472, 276, 'z', 32, 24, (0.769, 0.604, 0.239))
add_box('running_gear', 'front_right_shock_lower_mount_inner_tab', 853, 484, 349, 48, 18, 92, (0.722, 0.722, 0.722))
add_box('running_gear', 'front_right_shock_lower_mount_outer_tab', 853, 556, 349, 48, 18, 92, (0.722, 0.722, 0.722))
add_cylinder('running_gear', 'front_right_shock_lower_pin', 877, 520, 395, 'y', 30, 126, (0.769, 0.604, 0.239))
add_cylinder('running_gear', 'front_right_shock_lower_eye_bushing', 877, 520, 395, 'y', 72, 82, (0.114, 0.114, 0.114))
add_box('running_gear', 'front_right_shock_upper_tower_gusset_front', 901, 520, 765, 38, 118, 110, (0.176, 0.188, 0.200))
add_box('running_gear', 'front_right_shock_upper_tower_gusset_rear', 987, 520, 765, 38, 118, 110, (0.176, 0.188, 0.200))
add_cylinder('running_gear', 'front_right_shock_upper_pin', 945, 520, 855, 'y', 30, 146, (0.769, 0.604, 0.239))
add_cylinder('running_gear', 'front_right_shock_upper_eye_bushing', 945, 520, 855, 'y', 72, 86, (0.114, 0.114, 0.114))
add_mesh('running_gear', 'front_right_shock_centerline_connection_path', [(864.14, 499, 396.901), (889.86, 499, 393.099), (957.86, 499, 853.099), (932.14, 499, 856.901), (864.14, 541, 396.901), (889.86, 541, 393.099), (957.86, 541, 853.099), (932.14, 541, 856.901)], [(0, 1, 2, 3), (4, 7, 6, 5), (0, 4, 5, 1), (1, 5, 6, 2), (2, 6, 7, 3), (3, 7, 4, 0)], (0.486, 0.435, 0.796))
add_box('running_gear', 'front_right_bump_stop_axle_strike_pad', 590, 495, 476, 138, 105, 22, (0.722, 0.722, 0.722))
add_cylinder('datum', 'front_right_fixed_hanger_pin_center_datum', 262, 430, 430, 'y', 12, 170, (0.486, 0.435, 0.796))
add_cylinder('datum', 'front_right_shackle_upper_pin_center_datum', 1332, 430, 430, 'y', 12, 170, (0.486, 0.435, 0.796))
add_cylinder('datum', 'front_right_shackle_lower_pin_center_datum', 1261, 430, 356, 'y', 12, 152, (0.486, 0.435, 0.796))
add_cylinder('running_gear', 'rear_left_brake_backing_plate', 3020, -750, 395, 'y', 365, 55, (0.722, 0.722, 0.722))
add_cylinder('running_gear', 'rear_right_brake_backing_plate', 3020, 750, 395, 'y', 365, 55, (0.722, 0.722, 0.722))
add_box('running_gear', 'rear_left_leaf_spring_layer_1', 2500, -430, 305, 935, 78, 14, (0.133, 0.133, 0.133))
add_box('running_gear', 'rear_left_leaf_spring_layer_2', 2500, -430, 323, 820, 78, 14, (0.133, 0.133, 0.133))
add_box('running_gear', 'rear_left_leaf_spring_layer_3', 2500, -430, 341, 705, 78, 14, (0.133, 0.133, 0.133))
add_cylinder('running_gear', 'rear_left_u_bolt_1', 2955, -430, 405, 'z', 24, 210, (0.722, 0.722, 0.722))
add_cylinder('running_gear', 'rear_left_u_bolt_2', 3085, -430, 405, 'z', 24, 210, (0.722, 0.722, 0.722))
add_cylinder('running_gear', 'rear_left_fixed_spring_eye_bushing', 2547, -430, 430, 'y', 92, 96, (0.114, 0.114, 0.114))
add_cylinder('running_gear', 'rear_left_fixed_spring_eye_inner_sleeve', 2547, -430, 430, 'y', 38, 132, (0.722, 0.722, 0.722))
add_cylinder('chassis', 'left_rear_fixed_hanger_cross_sleeve', 2547, -432.5, 430, 'y', 44, 152, (0.722, 0.722, 0.722))
add_cylinder('chassis', 'left_rear_fixed_hanger_pin_bolt', 2547, -432.5, 430, 'y', 30, 190, (0.769, 0.604, 0.239))
add_box('chassis', 'left_rear_fixed_hanger_outer_bolt_head', 2529, -553, 412, 36, 18, 36, (0.769, 0.604, 0.239))
add_box('chassis', 'left_rear_fixed_hanger_inner_nut', 2529, -312, 412, 36, 18, 36, (0.769, 0.604, 0.239))
add_mesh('running_gear', 'rear_left_fixed_eye_leaf_wrap_upper', [(2557.78, -465, 438.932), (2536.22, -465, 421.068), (2594.22, -465, 351.068), (2615.78, -465, 368.932), (2557.78, -395, 438.932), (2536.22, -395, 421.068), (2594.22, -395, 351.068), (2615.78, -395, 368.932)], [(0, 1, 2, 3), (4, 7, 6, 5), (0, 4, 5, 1), (1, 5, 6, 2), (2, 6, 7, 3), (3, 7, 4, 0)], (0.133, 0.133, 0.133))
add_mesh('running_gear', 'rear_left_fixed_eye_leaf_wrap_lower', [(2553.8, -463, 420.644), (2540.2, -463, 403.356), (2648.2, -463, 318.356), (2661.8, -463, 335.644), (2553.8, -397, 420.644), (2540.2, -397, 403.356), (2648.2, -397, 318.356), (2661.8, -397, 335.644)], [(0, 1, 2, 3), (4, 7, 6, 5), (0, 4, 5, 1), (1, 5, 6, 2), (2, 6, 7, 3), (3, 7, 4, 0)], (0.133, 0.133, 0.133))
add_cylinder('chassis', 'left_rear_shackle_upper_frame_bushing', 3617, -432.5, 430, 'y', 86, 126, (0.114, 0.114, 0.114))
add_cylinder('chassis', 'left_rear_shackle_upper_sleeve', 3617, -432.5, 430, 'y', 36, 152, (0.722, 0.722, 0.722))
add_cylinder('running_gear', 'rear_left_shackle_lower_spring_eye_bushing', 3546, -430, 356, 'y', 92, 96, (0.114, 0.114, 0.114))
add_cylinder('running_gear', 'rear_left_shackle_lower_spring_eye_sleeve', 3546, -430, 356, 'y', 38, 132, (0.722, 0.722, 0.722))
add_mesh('running_gear', 'rear_left_shackle_outer_link_plate', [(3637.93, -516, 409.922), (3596.07, -516, 450.078), (3525.07, -516, 376.078), (3566.93, -516, 335.922), (3637.93, -498, 409.922), (3596.07, -498, 450.078), (3525.07, -498, 376.078), (3566.93, -498, 335.922)], [(0, 1, 2, 3), (4, 7, 6, 5), (0, 4, 5, 1), (1, 5, 6, 2), (2, 6, 7, 3), (3, 7, 4, 0)], (0.722, 0.722, 0.722))
add_mesh('running_gear', 'rear_left_shackle_inner_link_plate', [(3637.93, -369, 409.922), (3596.07, -369, 450.078), (3525.07, -369, 376.078), (3566.93, -369, 335.922), (3637.93, -351, 409.922), (3596.07, -351, 450.078), (3525.07, -351, 376.078), (3566.93, -351, 335.922)], [(0, 1, 2, 3), (4, 7, 6, 5), (0, 4, 5, 1), (1, 5, 6, 2), (2, 6, 7, 3), (3, 7, 4, 0)], (0.722, 0.722, 0.722))
add_cylinder('running_gear', 'rear_left_shackle_upper_pin_bolt', 3617, -432.5, 430, 'y', 30, 190, (0.769, 0.604, 0.239))
add_cylinder('running_gear', 'rear_left_shackle_lower_pin_bolt', 3546, -430, 356, 'y', 30, 168, (0.769, 0.604, 0.239))
add_mesh('running_gear', 'rear_left_shackle_eye_leaf_wrap_upper', [(3545.78, -465, 342.002), (3546.22, -465, 369.998), (3420.22, -465, 371.998), (3419.78, -465, 344.002), (3545.78, -395, 342.002), (3546.22, -395, 369.998), (3420.22, -395, 371.998), (3419.78, -395, 344.002)], [(0, 1, 2, 3), (4, 7, 6, 5), (0, 4, 5, 1), (1, 5, 6, 2), (2, 6, 7, 3), (3, 7, 4, 0)], (0.133, 0.133, 0.133))
add_mesh('running_gear', 'rear_left_shackle_eye_leaf_wrap_lower', [(3546.74, -463, 327.025), (3545.26, -463, 348.975), (3366.26, -463, 336.975), (3367.74, -463, 315.025), (3546.74, -397, 327.025), (3545.26, -397, 348.975), (3366.26, -397, 336.975), (3367.74, -397, 315.025)], [(0, 1, 2, 3), (4, 7, 6, 5), (0, 4, 5, 1), (1, 5, 6, 2), (2, 6, 7, 3), (3, 7, 4, 0)], (0.133, 0.133, 0.133))
add_box('running_gear', 'rear_left_leaf_pack_rebound_clip_1', 2688, -430, 300, 44, 98, 72, (0.722, 0.722, 0.722))
add_cylinder('running_gear', 'rear_left_leaf_pack_rebound_clip_1_bolt', 2710, -430, 352, 'y', 16, 112, (0.769, 0.604, 0.239))
add_box('running_gear', 'rear_left_leaf_pack_rebound_clip_2', 3313, -430, 300, 44, 98, 72, (0.722, 0.722, 0.722))
add_cylinder('running_gear', 'rear_left_leaf_pack_rebound_clip_2_bolt', 3335, -430, 352, 'y', 16, 112, (0.769, 0.604, 0.239))
add_cylinder('running_gear', 'rear_left_spring_center_bolt', 3020, -430, 338, 'z', 18, 88, (0.769, 0.604, 0.239))
add_box('running_gear', 'rear_left_axle_spring_perch_welded_saddle', 2938, -430, 352, 164, 126, 38, (0.722, 0.722, 0.722))
add_box('running_gear', 'rear_left_spring_perch_lower_clamp_plate', 2894, -430, 290, 252, 146, 34, (0.722, 0.722, 0.722))
add_box('running_gear', 'rear_left_axle_tube_contact_pad', 2928, -430, 452, 184, 132, 24, (0.722, 0.722, 0.722))
add_box('running_gear', 'rear_left_u_bolt_1_top_crown', 2932, -430, 490, 36, 118, 24, (0.722, 0.722, 0.722))
add_cylinder('running_gear', 'rear_left_u_bolt_1_leg_1', 2950, -472, 394, 'z', 18, 226, (0.722, 0.722, 0.722))
add_cylinder('running_gear', 'rear_left_u_bolt_1_leg_1_lower_nut', 2950, -472, 276, 'z', 32, 24, (0.769, 0.604, 0.239))
add_cylinder('running_gear', 'rear_left_u_bolt_1_leg_2', 2950, -388, 394, 'z', 18, 226, (0.722, 0.722, 0.722))
add_cylinder('running_gear', 'rear_left_u_bolt_1_leg_2_lower_nut', 2950, -388, 276, 'z', 32, 24, (0.769, 0.604, 0.239))
add_box('running_gear', 'rear_left_u_bolt_2_top_crown', 3072, -430, 490, 36, 118, 24, (0.722, 0.722, 0.722))
add_cylinder('running_gear', 'rear_left_u_bolt_2_leg_1', 3090, -472, 394, 'z', 18, 226, (0.722, 0.722, 0.722))
add_cylinder('running_gear', 'rear_left_u_bolt_2_leg_1_lower_nut', 3090, -472, 276, 'z', 32, 24, (0.769, 0.604, 0.239))
add_cylinder('running_gear', 'rear_left_u_bolt_2_leg_2', 3090, -388, 394, 'z', 18, 226, (0.722, 0.722, 0.722))
add_cylinder('running_gear', 'rear_left_u_bolt_2_leg_2_lower_nut', 3090, -388, 276, 'z', 32, 24, (0.769, 0.604, 0.239))
add_box('running_gear', 'rear_left_shock_lower_mount_inner_tab', 3138, -484, 349, 48, 18, 92, (0.722, 0.722, 0.722))
add_box('running_gear', 'rear_left_shock_lower_mount_outer_tab', 3138, -556, 349, 48, 18, 92, (0.722, 0.722, 0.722))
add_cylinder('running_gear', 'rear_left_shock_lower_pin', 3162, -520, 395, 'y', 30, 126, (0.769, 0.604, 0.239))
add_cylinder('running_gear', 'rear_left_shock_lower_eye_bushing', 3162, -520, 395, 'y', 72, 82, (0.114, 0.114, 0.114))
add_box('running_gear', 'rear_left_shock_upper_tower_gusset_front', 3186, -520, 765, 38, 118, 110, (0.176, 0.188, 0.200))
add_box('running_gear', 'rear_left_shock_upper_tower_gusset_rear', 3272, -520, 765, 38, 118, 110, (0.176, 0.188, 0.200))
add_cylinder('running_gear', 'rear_left_shock_upper_pin', 3230, -520, 855, 'y', 30, 146, (0.769, 0.604, 0.239))
add_cylinder('running_gear', 'rear_left_shock_upper_eye_bushing', 3230, -520, 855, 'y', 72, 86, (0.114, 0.114, 0.114))
add_mesh('running_gear', 'rear_left_shock_centerline_connection_path', [(3149.14, -541, 396.901), (3174.86, -541, 393.099), (3242.86, -541, 853.099), (3217.14, -541, 856.901), (3149.14, -499, 396.901), (3174.86, -499, 393.099), (3242.86, -499, 853.099), (3217.14, -499, 856.901)], [(0, 1, 2, 3), (4, 7, 6, 5), (0, 4, 5, 1), (1, 5, 6, 2), (2, 6, 7, 3), (3, 7, 4, 0)], (0.486, 0.435, 0.796))
add_box('running_gear', 'rear_left_bump_stop_axle_strike_pad', 2875, -495, 476, 138, 105, 22, (0.722, 0.722, 0.722))
add_cylinder('datum', 'rear_left_fixed_hanger_pin_center_datum', 2547, -430, 430, 'y', 12, 170, (0.486, 0.435, 0.796))
add_cylinder('datum', 'rear_left_shackle_upper_pin_center_datum', 3617, -430, 430, 'y', 12, 170, (0.486, 0.435, 0.796))
add_cylinder('datum', 'rear_left_shackle_lower_pin_center_datum', 3546, -430, 356, 'y', 12, 152, (0.486, 0.435, 0.796))
add_box('running_gear', 'rear_right_leaf_spring_layer_1', 2500, 430, 305, 935, 78, 14, (0.133, 0.133, 0.133))
add_box('running_gear', 'rear_right_leaf_spring_layer_2', 2500, 430, 323, 820, 78, 14, (0.133, 0.133, 0.133))
add_box('running_gear', 'rear_right_leaf_spring_layer_3', 2500, 430, 341, 705, 78, 14, (0.133, 0.133, 0.133))
add_cylinder('running_gear', 'rear_right_u_bolt_1', 2955, 430, 405, 'z', 24, 210, (0.722, 0.722, 0.722))
add_cylinder('running_gear', 'rear_right_u_bolt_2', 3085, 430, 405, 'z', 24, 210, (0.722, 0.722, 0.722))
add_cylinder('running_gear', 'rear_right_fixed_spring_eye_bushing', 2547, 430, 430, 'y', 92, 96, (0.114, 0.114, 0.114))
add_cylinder('running_gear', 'rear_right_fixed_spring_eye_inner_sleeve', 2547, 430, 430, 'y', 38, 132, (0.722, 0.722, 0.722))
add_cylinder('chassis', 'right_rear_fixed_hanger_cross_sleeve', 2547, 432.5, 430, 'y', 44, 152, (0.722, 0.722, 0.722))
add_cylinder('chassis', 'right_rear_fixed_hanger_pin_bolt', 2547, 432.5, 430, 'y', 30, 190, (0.769, 0.604, 0.239))
add_box('chassis', 'right_rear_fixed_hanger_outer_bolt_head', 2529, 553, 412, 36, 18, 36, (0.769, 0.604, 0.239))
add_box('chassis', 'right_rear_fixed_hanger_inner_nut', 2529, 312, 412, 36, 18, 36, (0.769, 0.604, 0.239))
add_mesh('running_gear', 'rear_right_fixed_eye_leaf_wrap_upper', [(2557.78, 395, 438.932), (2536.22, 395, 421.068), (2594.22, 395, 351.068), (2615.78, 395, 368.932), (2557.78, 465, 438.932), (2536.22, 465, 421.068), (2594.22, 465, 351.068), (2615.78, 465, 368.932)], [(0, 1, 2, 3), (4, 7, 6, 5), (0, 4, 5, 1), (1, 5, 6, 2), (2, 6, 7, 3), (3, 7, 4, 0)], (0.133, 0.133, 0.133))
add_mesh('running_gear', 'rear_right_fixed_eye_leaf_wrap_lower', [(2553.8, 397, 420.644), (2540.2, 397, 403.356), (2648.2, 397, 318.356), (2661.8, 397, 335.644), (2553.8, 463, 420.644), (2540.2, 463, 403.356), (2648.2, 463, 318.356), (2661.8, 463, 335.644)], [(0, 1, 2, 3), (4, 7, 6, 5), (0, 4, 5, 1), (1, 5, 6, 2), (2, 6, 7, 3), (3, 7, 4, 0)], (0.133, 0.133, 0.133))
add_cylinder('chassis', 'right_rear_shackle_upper_frame_bushing', 3617, 432.5, 430, 'y', 86, 126, (0.114, 0.114, 0.114))
add_cylinder('chassis', 'right_rear_shackle_upper_sleeve', 3617, 432.5, 430, 'y', 36, 152, (0.722, 0.722, 0.722))
add_cylinder('running_gear', 'rear_right_shackle_lower_spring_eye_bushing', 3546, 430, 356, 'y', 92, 96, (0.114, 0.114, 0.114))
add_cylinder('running_gear', 'rear_right_shackle_lower_spring_eye_sleeve', 3546, 430, 356, 'y', 38, 132, (0.722, 0.722, 0.722))
add_mesh('running_gear', 'rear_right_shackle_outer_link_plate', [(3637.93, 498, 409.922), (3596.07, 498, 450.078), (3525.07, 498, 376.078), (3566.93, 498, 335.922), (3637.93, 516, 409.922), (3596.07, 516, 450.078), (3525.07, 516, 376.078), (3566.93, 516, 335.922)], [(0, 1, 2, 3), (4, 7, 6, 5), (0, 4, 5, 1), (1, 5, 6, 2), (2, 6, 7, 3), (3, 7, 4, 0)], (0.722, 0.722, 0.722))
add_mesh('running_gear', 'rear_right_shackle_inner_link_plate', [(3637.93, 351, 409.922), (3596.07, 351, 450.078), (3525.07, 351, 376.078), (3566.93, 351, 335.922), (3637.93, 369, 409.922), (3596.07, 369, 450.078), (3525.07, 369, 376.078), (3566.93, 369, 335.922)], [(0, 1, 2, 3), (4, 7, 6, 5), (0, 4, 5, 1), (1, 5, 6, 2), (2, 6, 7, 3), (3, 7, 4, 0)], (0.722, 0.722, 0.722))
add_cylinder('running_gear', 'rear_right_shackle_upper_pin_bolt', 3617, 432.5, 430, 'y', 30, 190, (0.769, 0.604, 0.239))
add_cylinder('running_gear', 'rear_right_shackle_lower_pin_bolt', 3546, 430, 356, 'y', 30, 168, (0.769, 0.604, 0.239))
add_mesh('running_gear', 'rear_right_shackle_eye_leaf_wrap_upper', [(3545.78, 395, 342.002), (3546.22, 395, 369.998), (3420.22, 395, 371.998), (3419.78, 395, 344.002), (3545.78, 465, 342.002), (3546.22, 465, 369.998), (3420.22, 465, 371.998), (3419.78, 465, 344.002)], [(0, 1, 2, 3), (4, 7, 6, 5), (0, 4, 5, 1), (1, 5, 6, 2), (2, 6, 7, 3), (3, 7, 4, 0)], (0.133, 0.133, 0.133))
add_mesh('running_gear', 'rear_right_shackle_eye_leaf_wrap_lower', [(3546.74, 397, 327.025), (3545.26, 397, 348.975), (3366.26, 397, 336.975), (3367.74, 397, 315.025), (3546.74, 463, 327.025), (3545.26, 463, 348.975), (3366.26, 463, 336.975), (3367.74, 463, 315.025)], [(0, 1, 2, 3), (4, 7, 6, 5), (0, 4, 5, 1), (1, 5, 6, 2), (2, 6, 7, 3), (3, 7, 4, 0)], (0.133, 0.133, 0.133))
add_box('running_gear', 'rear_right_leaf_pack_rebound_clip_1', 2688, 430, 300, 44, 98, 72, (0.722, 0.722, 0.722))
add_cylinder('running_gear', 'rear_right_leaf_pack_rebound_clip_1_bolt', 2710, 430, 352, 'y', 16, 112, (0.769, 0.604, 0.239))
add_box('running_gear', 'rear_right_leaf_pack_rebound_clip_2', 3313, 430, 300, 44, 98, 72, (0.722, 0.722, 0.722))
add_cylinder('running_gear', 'rear_right_leaf_pack_rebound_clip_2_bolt', 3335, 430, 352, 'y', 16, 112, (0.769, 0.604, 0.239))
add_cylinder('running_gear', 'rear_right_spring_center_bolt', 3020, 430, 338, 'z', 18, 88, (0.769, 0.604, 0.239))
add_box('running_gear', 'rear_right_axle_spring_perch_welded_saddle', 2938, 430, 352, 164, 126, 38, (0.722, 0.722, 0.722))
add_box('running_gear', 'rear_right_spring_perch_lower_clamp_plate', 2894, 430, 290, 252, 146, 34, (0.722, 0.722, 0.722))
add_box('running_gear', 'rear_right_axle_tube_contact_pad', 2928, 430, 452, 184, 132, 24, (0.722, 0.722, 0.722))
add_box('running_gear', 'rear_right_u_bolt_1_top_crown', 2932, 430, 490, 36, 118, 24, (0.722, 0.722, 0.722))
add_cylinder('running_gear', 'rear_right_u_bolt_1_leg_1', 2950, 388, 394, 'z', 18, 226, (0.722, 0.722, 0.722))
add_cylinder('running_gear', 'rear_right_u_bolt_1_leg_1_lower_nut', 2950, 388, 276, 'z', 32, 24, (0.769, 0.604, 0.239))
add_cylinder('running_gear', 'rear_right_u_bolt_1_leg_2', 2950, 472, 394, 'z', 18, 226, (0.722, 0.722, 0.722))
add_cylinder('running_gear', 'rear_right_u_bolt_1_leg_2_lower_nut', 2950, 472, 276, 'z', 32, 24, (0.769, 0.604, 0.239))
add_box('running_gear', 'rear_right_u_bolt_2_top_crown', 3072, 430, 490, 36, 118, 24, (0.722, 0.722, 0.722))
add_cylinder('running_gear', 'rear_right_u_bolt_2_leg_1', 3090, 388, 394, 'z', 18, 226, (0.722, 0.722, 0.722))
add_cylinder('running_gear', 'rear_right_u_bolt_2_leg_1_lower_nut', 3090, 388, 276, 'z', 32, 24, (0.769, 0.604, 0.239))
add_cylinder('running_gear', 'rear_right_u_bolt_2_leg_2', 3090, 472, 394, 'z', 18, 226, (0.722, 0.722, 0.722))
add_cylinder('running_gear', 'rear_right_u_bolt_2_leg_2_lower_nut', 3090, 472, 276, 'z', 32, 24, (0.769, 0.604, 0.239))
add_box('running_gear', 'rear_right_shock_lower_mount_inner_tab', 3138, 484, 349, 48, 18, 92, (0.722, 0.722, 0.722))
add_box('running_gear', 'rear_right_shock_lower_mount_outer_tab', 3138, 556, 349, 48, 18, 92, (0.722, 0.722, 0.722))
add_cylinder('running_gear', 'rear_right_shock_lower_pin', 3162, 520, 395, 'y', 30, 126, (0.769, 0.604, 0.239))
add_cylinder('running_gear', 'rear_right_shock_lower_eye_bushing', 3162, 520, 395, 'y', 72, 82, (0.114, 0.114, 0.114))
add_box('running_gear', 'rear_right_shock_upper_tower_gusset_front', 3186, 520, 765, 38, 118, 110, (0.176, 0.188, 0.200))
add_box('running_gear', 'rear_right_shock_upper_tower_gusset_rear', 3272, 520, 765, 38, 118, 110, (0.176, 0.188, 0.200))
add_cylinder('running_gear', 'rear_right_shock_upper_pin', 3230, 520, 855, 'y', 30, 146, (0.769, 0.604, 0.239))
add_cylinder('running_gear', 'rear_right_shock_upper_eye_bushing', 3230, 520, 855, 'y', 72, 86, (0.114, 0.114, 0.114))
add_mesh('running_gear', 'rear_right_shock_centerline_connection_path', [(3149.14, 499, 396.901), (3174.86, 499, 393.099), (3242.86, 499, 853.099), (3217.14, 499, 856.901), (3149.14, 541, 396.901), (3174.86, 541, 393.099), (3242.86, 541, 853.099), (3217.14, 541, 856.901)], [(0, 1, 2, 3), (4, 7, 6, 5), (0, 4, 5, 1), (1, 5, 6, 2), (2, 6, 7, 3), (3, 7, 4, 0)], (0.486, 0.435, 0.796))
add_box('running_gear', 'rear_right_bump_stop_axle_strike_pad', 2875, 495, 476, 138, 105, 22, (0.722, 0.722, 0.722))
add_cylinder('datum', 'rear_right_fixed_hanger_pin_center_datum', 2547, 430, 430, 'y', 12, 170, (0.486, 0.435, 0.796))
add_cylinder('datum', 'rear_right_shackle_upper_pin_center_datum', 3617, 430, 430, 'y', 12, 170, (0.486, 0.435, 0.796))
add_cylinder('datum', 'rear_right_shackle_lower_pin_center_datum', 3546, 430, 356, 'y', 12, 152, (0.486, 0.435, 0.796))
add_cylinder('brake_system', 'front_left_vented_disc_rotor', 735, -738, 395, 'y', 405, 42, (0.722, 0.722, 0.722))
add_box('brake_system', 'front_left_sumitomo_disc_caliper_body', 827, -760, 477, 140, 94, 225, (0.722, 0.722, 0.722))
add_box('brake_system', 'front_left_disc_caliper_bridge', 781, -787, 583, 92, 68, 52, (0.722, 0.722, 0.722))
add_cylinder('brake_system', 'front_left_caliper_bleeder_screw', 857, -824, 617, 'y', 18, 42, (0.769, 0.604, 0.239))
add_cylinder('brake_system', 'front_left_flex_hose_to_caliper', 820, -652, 580, 'y', 22, 245, (0.114, 0.114, 0.114))
add_cylinder('brake_system', 'front_right_vented_disc_rotor', 735, 738, 395, 'y', 405, 42, (0.722, 0.722, 0.722))
add_box('brake_system', 'front_right_sumitomo_disc_caliper_body', 827, 760, 477, 140, 94, 225, (0.722, 0.722, 0.722))
add_box('brake_system', 'front_right_disc_caliper_bridge', 781, 787, 583, 92, 68, 52, (0.722, 0.722, 0.722))
add_cylinder('brake_system', 'front_right_caliper_bleeder_screw', 857, 824, 617, 'y', 18, 42, (0.769, 0.604, 0.239))
add_cylinder('brake_system', 'front_right_flex_hose_to_caliper', 820, 652, 580, 'y', 22, 245, (0.114, 0.114, 0.114))
add_cylinder('running_gear', 'front_left_outer_rim_ring', 735, -845, 395, 'y', 455, 34, (0.722, 0.722, 0.722))
add_cylinder('running_gear', 'front_left_inner_rim_shadow', 735, -855, 395, 'y', 315, 22, (0.114, 0.114, 0.114))
add_cylinder('running_gear', 'front_left_valve_stem', 865, -870, 540, 'y', 22, 50, (0.114, 0.114, 0.114))
add_cylinder('running_gear', 'front_left_lug_nut_1', 827, -877, 395, 'y', 32, 36, (0.722, 0.722, 0.722))
add_cylinder('running_gear', 'front_left_lug_nut_2', 781, -877, 474.674, 'y', 32, 36, (0.722, 0.722, 0.722))
add_cylinder('running_gear', 'front_left_lug_nut_3', 689, -877, 474.674, 'y', 32, 36, (0.722, 0.722, 0.722))
add_cylinder('running_gear', 'front_left_lug_nut_4', 643, -877, 395, 'y', 32, 36, (0.722, 0.722, 0.722))
add_cylinder('running_gear', 'front_left_lug_nut_5', 689, -877, 315.326, 'y', 32, 36, (0.722, 0.722, 0.722))
add_cylinder('running_gear', 'front_left_lug_nut_6', 781, -877, 315.326, 'y', 32, 36, (0.722, 0.722, 0.722))
add_box('running_gear', 'front_left_mud_terrain_sidewall_lettering_panel', 925, -899, 103, 165, 18, 34, (0.616, 0.588, 0.494))
add_cylinder('running_gear', 'front_right_outer_rim_ring', 735, 845, 395, 'y', 455, 34, (0.722, 0.722, 0.722))
add_cylinder('running_gear', 'front_right_inner_rim_shadow', 735, 855, 395, 'y', 315, 22, (0.114, 0.114, 0.114))
add_cylinder('running_gear', 'front_right_valve_stem', 865, 870, 540, 'y', 22, 50, (0.114, 0.114, 0.114))
add_cylinder('running_gear', 'front_right_lug_nut_1', 827, 877, 395, 'y', 32, 36, (0.722, 0.722, 0.722))
add_cylinder('running_gear', 'front_right_lug_nut_2', 781, 877, 474.674, 'y', 32, 36, (0.722, 0.722, 0.722))
add_cylinder('running_gear', 'front_right_lug_nut_3', 689, 877, 474.674, 'y', 32, 36, (0.722, 0.722, 0.722))
add_cylinder('running_gear', 'front_right_lug_nut_4', 643, 877, 395, 'y', 32, 36, (0.722, 0.722, 0.722))
add_cylinder('running_gear', 'front_right_lug_nut_5', 689, 877, 315.326, 'y', 32, 36, (0.722, 0.722, 0.722))
add_cylinder('running_gear', 'front_right_lug_nut_6', 781, 877, 315.326, 'y', 32, 36, (0.722, 0.722, 0.722))
add_box('running_gear', 'front_right_mud_terrain_sidewall_lettering_panel', 925, 899, 103, 165, 18, 34, (0.616, 0.588, 0.494))
add_cylinder('running_gear', 'rear_left_outer_rim_ring', 3020, -845, 395, 'y', 455, 34, (0.722, 0.722, 0.722))
add_cylinder('running_gear', 'rear_left_inner_rim_shadow', 3020, -855, 395, 'y', 315, 22, (0.114, 0.114, 0.114))
add_cylinder('running_gear', 'rear_left_valve_stem', 3150, -870, 540, 'y', 22, 50, (0.114, 0.114, 0.114))
add_cylinder('running_gear', 'rear_left_lug_nut_1', 3112, -877, 395, 'y', 32, 36, (0.722, 0.722, 0.722))
add_cylinder('running_gear', 'rear_left_lug_nut_2', 3066, -877, 474.674, 'y', 32, 36, (0.722, 0.722, 0.722))
add_cylinder('running_gear', 'rear_left_lug_nut_3', 2974, -877, 474.674, 'y', 32, 36, (0.722, 0.722, 0.722))
add_cylinder('running_gear', 'rear_left_lug_nut_4', 2928, -877, 395, 'y', 32, 36, (0.722, 0.722, 0.722))
add_cylinder('running_gear', 'rear_left_lug_nut_5', 2974, -877, 315.326, 'y', 32, 36, (0.722, 0.722, 0.722))
add_cylinder('running_gear', 'rear_left_lug_nut_6', 3066, -877, 315.326, 'y', 32, 36, (0.722, 0.722, 0.722))
add_box('running_gear', 'rear_left_mud_terrain_sidewall_lettering_panel', 3210, -899, 103, 165, 18, 34, (0.616, 0.588, 0.494))
add_cylinder('running_gear', 'rear_right_outer_rim_ring', 3020, 845, 395, 'y', 455, 34, (0.722, 0.722, 0.722))
add_cylinder('running_gear', 'rear_right_inner_rim_shadow', 3020, 855, 395, 'y', 315, 22, (0.114, 0.114, 0.114))
add_cylinder('running_gear', 'rear_right_valve_stem', 3150, 870, 540, 'y', 22, 50, (0.114, 0.114, 0.114))
add_cylinder('running_gear', 'rear_right_lug_nut_1', 3112, 877, 395, 'y', 32, 36, (0.722, 0.722, 0.722))
add_cylinder('running_gear', 'rear_right_lug_nut_2', 3066, 877, 474.674, 'y', 32, 36, (0.722, 0.722, 0.722))
add_cylinder('running_gear', 'rear_right_lug_nut_3', 2974, 877, 474.674, 'y', 32, 36, (0.722, 0.722, 0.722))
add_cylinder('running_gear', 'rear_right_lug_nut_4', 2928, 877, 395, 'y', 32, 36, (0.722, 0.722, 0.722))
add_cylinder('running_gear', 'rear_right_lug_nut_5', 2974, 877, 315.326, 'y', 32, 36, (0.722, 0.722, 0.722))
add_cylinder('running_gear', 'rear_right_lug_nut_6', 3066, 877, 315.326, 'y', 32, 36, (0.722, 0.722, 0.722))
add_box('running_gear', 'rear_right_mud_terrain_sidewall_lettering_panel', 3210, 899, 103, 165, 18, 34, (0.616, 0.588, 0.494))
add_cylinder('brake_system', 'front_hard_line_right_frame_run', 1180, 338, 575, 'x', 18, 1650, (0.722, 0.722, 0.722))
add_cylinder('brake_system', 'rear_hard_line_right_frame_run', 2320, 338, 575, 'x', 18, 1500, (0.722, 0.722, 0.722))
add_cylinder('brake_system', 'rear_axle_brake_line', 3020, 0, 520, 'y', 18, 1280, (0.722, 0.722, 0.722))
add_cylinder('brake_system', 'parking_brake_front_cable', 1630, -145, 545, 'x', 22, 650, (0.114, 0.114, 0.114))
add_box('brake_system', 'parking_brake_equalizer_bar', 2295, 0, 548, 175, 46, 24, (0.722, 0.722, 0.722))
add_cylinder('brake_system', 'parking_brake_equalizer_pivot_pin', 2380, 0, 548, 'y', 26, 120, (0.722, 0.722, 0.722))
add_cylinder('brake_system', 'left_rear_parking_brake_cable', 2685, -360, 535, 'x', 22, 760, (0.114, 0.114, 0.114))
add_box('brake_system', 'left_parking_brake_clevis', 3035, -520, 548, 66, 32, 34, (0.769, 0.604, 0.239))
add_cylinder('brake_system', 'left_parking_brake_return_spring', 2945, -520, 602, 'x', 34, 170, (0.133, 0.133, 0.133))
add_box('brake_system', 'left_parking_brake_cable_clip_1', 2485, -430, 545, 38, 30, 34, (0.722, 0.722, 0.722))
add_box('brake_system', 'left_parking_brake_cable_clip_2', 2805, -470, 545, 38, 30, 34, (0.722, 0.722, 0.722))
add_cylinder('brake_system', 'right_rear_parking_brake_cable', 2685, 360, 535, 'x', 22, 760, (0.114, 0.114, 0.114))
add_box('brake_system', 'right_parking_brake_clevis', 3035, 520, 548, 66, 32, 34, (0.769, 0.604, 0.239))
add_cylinder('brake_system', 'right_parking_brake_return_spring', 2945, 520, 602, 'x', 34, 170, (0.133, 0.133, 0.133))
add_box('brake_system', 'right_parking_brake_cable_clip_1', 2485, 430, 545, 38, 30, 34, (0.722, 0.722, 0.722))
add_box('brake_system', 'right_parking_brake_cable_clip_2', 2805, 470, 545, 38, 30, 34, (0.722, 0.722, 0.722))
add_box('body', 'transmission_tunnel', 1250, 0, 660, 1100, 360, 235, (0.812, 0.776, 0.667))
add_box('body', 'rear_load_floor', 2060, 0, 690, 1180, 1230, 42, (0.812, 0.776, 0.667))
add_box('body', 'rear_floor_longitudinal_rib_1', 2050, -420, 740, 1230, 38, 42, (0.812, 0.776, 0.667))
add_box('body', 'rear_floor_longitudinal_rib_2', 2050, -210, 740, 1230, 38, 42, (0.812, 0.776, 0.667))
add_box('body', 'rear_floor_longitudinal_rib_3', 2050, 0, 740, 1230, 38, 42, (0.812, 0.776, 0.667))
add_box('body', 'rear_floor_longitudinal_rib_4', 2050, 210, 740, 1230, 38, 42, (0.812, 0.776, 0.667))
add_box('body', 'rear_floor_longitudinal_rib_5', 2050, 420, 740, 1230, 38, 42, (0.812, 0.776, 0.667))
add_box('body', 'floor_cross_pressing_1', 980, 0, 735, 42, 1260, 34, (0.812, 0.776, 0.667))
add_box('body', 'floor_cross_pressing_2', 1280, 0, 735, 42, 1260, 34, (0.812, 0.776, 0.667))
add_box('body', 'floor_cross_pressing_3', 1730, 0, 735, 42, 1260, 34, (0.812, 0.776, 0.667))
add_box('body', 'floor_cross_pressing_4', 2140, 0, 735, 42, 1260, 34, (0.812, 0.776, 0.667))
add_box('body', 'floor_cross_pressing_5', 2570, 0, 735, 42, 1260, 34, (0.812, 0.776, 0.667))
add_box('body', 'floor_cross_pressing_6', 3020, 0, 735, 42, 1260, 34, (0.812, 0.776, 0.667))
add_box('body', 'left_front_wheel_arch_shadow', 365, -735, 745, 740, 34, 405, (0.114, 0.114, 0.114))
add_box('body', 'left_rear_wheel_arch_shadow', 2690, -735, 745, 690, 34, 410, (0.114, 0.114, 0.114))
add_box('body', 'left_rear_inner_wheel_tub', 2655, -505, 755, 750, 280, 385, (0.812, 0.776, 0.667))
add_box('body', 'left_tub_top_capping', 1960, -805, 1322, 1530, 105, 58, (0.812, 0.776, 0.667))
add_box('body', 'left_door_outer_skin_lower_pressing', 1235, -790, 845, 725, 34, 105, (0.812, 0.776, 0.667))
add_box('body', 'left_door_vertical_shut_gap_front', 1130, -824, 780, 18, 28, 780, (0.114, 0.114, 0.114))
add_box('body', 'left_door_vertical_shut_gap_rear', 1940, -824, 780, 18, 28, 780, (0.114, 0.114, 0.114))
add_box('body', 'left_mirror_arm', 1210, -884, 1240, 210, 26, 32, (0.722, 0.722, 0.722))
add_box('body', 'left_door_mirror_head', 1405, -930, 1195, 135, 42, 110, (0.910, 0.910, 0.910))
add_cylinder('body', 'left_fuel_or_body_plug_reference', 2935, -812, 1065, 'y', 115, 28, (0.722, 0.722, 0.722))
add_box('body', 'right_front_wheel_arch_shadow', 365, 735, 745, 740, 34, 405, (0.114, 0.114, 0.114))
add_box('body', 'right_rear_wheel_arch_shadow', 2690, 735, 745, 690, 34, 410, (0.114, 0.114, 0.114))
add_box('body', 'right_rear_inner_wheel_tub', 2655, 505, 755, 750, 280, 385, (0.812, 0.776, 0.667))
add_box('body', 'right_tub_top_capping', 1960, 805, 1322, 1530, 105, 58, (0.812, 0.776, 0.667))
add_box('body', 'right_door_outer_skin_lower_pressing', 1235, 790, 845, 725, 34, 105, (0.812, 0.776, 0.667))
add_box('body', 'right_door_vertical_shut_gap_front', 1130, 824, 780, 18, 28, 780, (0.114, 0.114, 0.114))
add_box('body', 'right_door_vertical_shut_gap_rear', 1940, 824, 780, 18, 28, 780, (0.114, 0.114, 0.114))
add_box('body', 'right_mirror_arm', 1210, 884, 1240, 210, 26, 32, (0.722, 0.722, 0.722))
add_box('body', 'right_door_mirror_head', 1405, 930, 1195, 135, 42, 110, (0.910, 0.910, 0.910))
add_cylinder('body', 'right_fuel_or_body_plug_reference', 2935, 812, 1065, 'y', 115, 28, (0.722, 0.722, 0.722))
add_cylinder('body', 'tailgate_hinge_or_chain_anchor_1', 3450, -610, 800, 'x', 54, 42, (0.722, 0.722, 0.722))
add_cylinder('body', 'tailgate_hinge_or_chain_anchor_2', 3450, -430, 1185, 'x', 54, 42, (0.722, 0.722, 0.722))
add_cylinder('body', 'tailgate_hinge_or_chain_anchor_3', 3450, 430, 1185, 'x', 54, 42, (0.722, 0.722, 0.722))
add_cylinder('body', 'tailgate_hinge_or_chain_anchor_4', 3450, 610, 800, 'x', 54, 42, (0.722, 0.722, 0.722))
add_box('body', 'tailgate_lower_pressed_panel', 3438, 0, 800, 38, 1190, 135, (0.812, 0.776, 0.667))
add_box('body', 'tailgate_upper_pressed_panel', 3438, 0, 1115, 38, 1190, 120, (0.812, 0.776, 0.667))
add_cylinder('body', 'rear_spare_tire', 3605, 0, 1020, 'x', 720, 230, (0.114, 0.114, 0.114))
add_cylinder('body', 'rear_spare_wheel_rim', 3615, 0, 1020, 'x', 385, 245, (0.722, 0.722, 0.722))
add_box('body', 'spare_wheel_carrier_vertical', 3520, 0, 800, 55, 72, 580, (0.722, 0.722, 0.722))
add_box('body', 'spare_wheel_carrier_crossbar', 3515, 0, 1015, 55, 560, 55, (0.722, 0.722, 0.722))
add_cylinder('body', 'left_rear_tail_lamp', 3470, -675, 930, 'x', 98, 38, (0.839, 0.278, 0.216))
add_cylinder('body', 'right_rear_tail_lamp', 3470, 675, 930, 'x', 98, 38, (0.839, 0.278, 0.216))
add_box('body', 'rear_license_plate', 3505, 0, 695, 24, 360, 170, (0.910, 0.910, 0.910))
add_box('body', 'rear_license_plate_bsn453_1_B_top', 3522, -107.5, 727.5, 8, 34, 7, (0.067, 0.075, 0.082))
add_box('body', 'rear_license_plate_bsn453_1_B_mid', 3522, -107.5, 695, 8, 34, 7, (0.067, 0.075, 0.082))
add_box('body', 'rear_license_plate_bsn453_1_B_bottom', 3522, -107.5, 662.5, 8, 34, 7, (0.067, 0.075, 0.082))
add_box('body', 'rear_license_plate_bsn453_1_B_ul', 3522, -121, 713, 8, 7, 36, (0.067, 0.075, 0.082))
add_box('body', 'rear_license_plate_bsn453_1_B_ll', 3522, -121, 677, 8, 7, 36, (0.067, 0.075, 0.082))
add_box('body', 'rear_license_plate_bsn453_1_B_ur', 3522, -94, 713, 8, 7, 36, (0.067, 0.075, 0.082))
add_box('body', 'rear_license_plate_bsn453_1_B_lr', 3522, -94, 677, 8, 7, 36, (0.067, 0.075, 0.082))
add_box('body', 'rear_license_plate_bsn453_2_S_top', 3522, -64.5, 727.5, 8, 34, 7, (0.067, 0.075, 0.082))
add_box('body', 'rear_license_plate_bsn453_2_S_mid', 3522, -64.5, 695, 8, 34, 7, (0.067, 0.075, 0.082))
add_box('body', 'rear_license_plate_bsn453_2_S_bottom', 3522, -64.5, 662.5, 8, 34, 7, (0.067, 0.075, 0.082))
add_box('body', 'rear_license_plate_bsn453_2_S_ul', 3522, -78, 713, 8, 7, 36, (0.067, 0.075, 0.082))
add_box('body', 'rear_license_plate_bsn453_2_S_lr', 3522, -51, 677, 8, 7, 36, (0.067, 0.075, 0.082))
add_box('body', 'rear_license_plate_bsn453_3_N_ul', 3522, -35, 713, 8, 7, 36, (0.067, 0.075, 0.082))
add_box('body', 'rear_license_plate_bsn453_3_N_ll', 3522, -35, 677, 8, 7, 36, (0.067, 0.075, 0.082))
add_box('body', 'rear_license_plate_bsn453_3_N_ur', 3522, -8, 713, 8, 7, 36, (0.067, 0.075, 0.082))
add_box('body', 'rear_license_plate_bsn453_3_N_lr', 3522, -8, 677, 8, 7, 36, (0.067, 0.075, 0.082))
add_box('body', 'rear_license_plate_bsn453_3_N_center', 3522, -21.5, 695, 8, 7, 72, (0.067, 0.075, 0.082))
add_box('body', 'rear_license_plate_bsn453_4_4_ul', 3522, 8, 713, 8, 7, 36, (0.067, 0.075, 0.082))
add_box('body', 'rear_license_plate_bsn453_4_4_ur', 3522, 35, 713, 8, 7, 36, (0.067, 0.075, 0.082))
add_box('body', 'rear_license_plate_bsn453_4_4_mid', 3522, 21.5, 695, 8, 34, 7, (0.067, 0.075, 0.082))
add_box('body', 'rear_license_plate_bsn453_4_4_lr', 3522, 35, 677, 8, 7, 36, (0.067, 0.075, 0.082))
add_box('body', 'rear_license_plate_bsn453_5_5_top', 3522, 64.5, 727.5, 8, 34, 7, (0.067, 0.075, 0.082))
add_box('body', 'rear_license_plate_bsn453_5_5_ul', 3522, 51, 713, 8, 7, 36, (0.067, 0.075, 0.082))
add_box('body', 'rear_license_plate_bsn453_5_5_mid', 3522, 64.5, 695, 8, 34, 7, (0.067, 0.075, 0.082))
add_box('body', 'rear_license_plate_bsn453_5_5_lr', 3522, 78, 677, 8, 7, 36, (0.067, 0.075, 0.082))
add_box('body', 'rear_license_plate_bsn453_5_5_bottom', 3522, 64.5, 662.5, 8, 34, 7, (0.067, 0.075, 0.082))
add_box('body', 'rear_license_plate_bsn453_6_3_top', 3522, 107.5, 727.5, 8, 34, 7, (0.067, 0.075, 0.082))
add_box('body', 'rear_license_plate_bsn453_6_3_ur', 3522, 121, 713, 8, 7, 36, (0.067, 0.075, 0.082))
add_box('body', 'rear_license_plate_bsn453_6_3_mid', 3522, 107.5, 695, 8, 34, 7, (0.067, 0.075, 0.082))
add_box('body', 'rear_license_plate_bsn453_6_3_lr', 3522, 121, 677, 8, 7, 36, (0.067, 0.075, 0.082))
add_box('body', 'rear_license_plate_bsn453_6_3_bottom', 3522, 107.5, 662.5, 8, 34, 7, (0.067, 0.075, 0.082))
add_box('front_detail', 'vertical_grille_slot_1', 82, -300, 842, 26, 42, 230, (0.114, 0.114, 0.114))
add_box('front_detail', 'vertical_grille_slot_2', 82, -200, 842, 26, 42, 230, (0.114, 0.114, 0.114))
add_box('front_detail', 'vertical_grille_slot_3', 82, -100, 842, 26, 42, 230, (0.114, 0.114, 0.114))
add_box('front_detail', 'vertical_grille_slot_4', 82, 0, 842, 26, 42, 230, (0.114, 0.114, 0.114))
add_box('front_detail', 'vertical_grille_slot_5', 82, 100, 842, 26, 42, 230, (0.114, 0.114, 0.114))
add_box('front_detail', 'vertical_grille_slot_6', 82, 200, 842, 26, 42, 230, (0.114, 0.114, 0.114))
add_box('front_detail', 'vertical_grille_slot_7', 82, 300, 842, 26, 42, 230, (0.114, 0.114, 0.114))
add_cylinder('front_detail', 'headlamp_bezel_left', 80, -495, 985, 'x', 270, 28, (0.722, 0.722, 0.722))
add_cylinder('front_detail', 'side_marker_left', 188, -683.1, 1005, 'y', 82, 26, (0.839, 0.278, 0.216))
add_cylinder('front_detail', 'headlamp_bezel_right', 80, 495, 985, 'x', 270, 28, (0.722, 0.722, 0.722))
add_cylinder('front_detail', 'side_marker_right', 188, 683.1, 1005, 'y', 82, 26, (0.839, 0.278, 0.216))
add_box('front_detail', 'front_license_plate', 5, 0, 650, 22, 360, 170, (0.910, 0.910, 0.910))
add_box('front_detail', 'front_license_plate_bsn453_1_B_top', -10, -107.5, 682.5, 8, 34, 7, (0.067, 0.075, 0.082))
add_box('front_detail', 'front_license_plate_bsn453_1_B_mid', -10, -107.5, 650, 8, 34, 7, (0.067, 0.075, 0.082))
add_box('front_detail', 'front_license_plate_bsn453_1_B_bottom', -10, -107.5, 617.5, 8, 34, 7, (0.067, 0.075, 0.082))
add_box('front_detail', 'front_license_plate_bsn453_1_B_ul', -10, -121, 668, 8, 7, 36, (0.067, 0.075, 0.082))
add_box('front_detail', 'front_license_plate_bsn453_1_B_ll', -10, -121, 632, 8, 7, 36, (0.067, 0.075, 0.082))
add_box('front_detail', 'front_license_plate_bsn453_1_B_ur', -10, -94, 668, 8, 7, 36, (0.067, 0.075, 0.082))
add_box('front_detail', 'front_license_plate_bsn453_1_B_lr', -10, -94, 632, 8, 7, 36, (0.067, 0.075, 0.082))
add_box('front_detail', 'front_license_plate_bsn453_2_S_top', -10, -64.5, 682.5, 8, 34, 7, (0.067, 0.075, 0.082))
add_box('front_detail', 'front_license_plate_bsn453_2_S_mid', -10, -64.5, 650, 8, 34, 7, (0.067, 0.075, 0.082))
add_box('front_detail', 'front_license_plate_bsn453_2_S_bottom', -10, -64.5, 617.5, 8, 34, 7, (0.067, 0.075, 0.082))
add_box('front_detail', 'front_license_plate_bsn453_2_S_ul', -10, -78, 668, 8, 7, 36, (0.067, 0.075, 0.082))
add_box('front_detail', 'front_license_plate_bsn453_2_S_lr', -10, -51, 632, 8, 7, 36, (0.067, 0.075, 0.082))
add_box('front_detail', 'front_license_plate_bsn453_3_N_ul', -10, -35, 668, 8, 7, 36, (0.067, 0.075, 0.082))
add_box('front_detail', 'front_license_plate_bsn453_3_N_ll', -10, -35, 632, 8, 7, 36, (0.067, 0.075, 0.082))
add_box('front_detail', 'front_license_plate_bsn453_3_N_ur', -10, -8, 668, 8, 7, 36, (0.067, 0.075, 0.082))
add_box('front_detail', 'front_license_plate_bsn453_3_N_lr', -10, -8, 632, 8, 7, 36, (0.067, 0.075, 0.082))
add_box('front_detail', 'front_license_plate_bsn453_3_N_center', -10, -21.5, 650, 8, 7, 72, (0.067, 0.075, 0.082))
add_box('front_detail', 'front_license_plate_bsn453_4_4_ul', -10, 8, 668, 8, 7, 36, (0.067, 0.075, 0.082))
add_box('front_detail', 'front_license_plate_bsn453_4_4_ur', -10, 35, 668, 8, 7, 36, (0.067, 0.075, 0.082))
add_box('front_detail', 'front_license_plate_bsn453_4_4_mid', -10, 21.5, 650, 8, 34, 7, (0.067, 0.075, 0.082))
add_box('front_detail', 'front_license_plate_bsn453_4_4_lr', -10, 35, 632, 8, 7, 36, (0.067, 0.075, 0.082))
add_box('front_detail', 'front_license_plate_bsn453_5_5_top', -10, 64.5, 682.5, 8, 34, 7, (0.067, 0.075, 0.082))
add_box('front_detail', 'front_license_plate_bsn453_5_5_ul', -10, 51, 668, 8, 7, 36, (0.067, 0.075, 0.082))
add_box('front_detail', 'front_license_plate_bsn453_5_5_mid', -10, 64.5, 650, 8, 34, 7, (0.067, 0.075, 0.082))
add_box('front_detail', 'front_license_plate_bsn453_5_5_lr', -10, 78, 632, 8, 7, 36, (0.067, 0.075, 0.082))
add_box('front_detail', 'front_license_plate_bsn453_5_5_bottom', -10, 64.5, 617.5, 8, 34, 7, (0.067, 0.075, 0.082))
add_box('front_detail', 'front_license_plate_bsn453_6_3_top', -10, 107.5, 682.5, 8, 34, 7, (0.067, 0.075, 0.082))
add_box('front_detail', 'front_license_plate_bsn453_6_3_ur', -10, 121, 668, 8, 7, 36, (0.067, 0.075, 0.082))
add_box('front_detail', 'front_license_plate_bsn453_6_3_mid', -10, 107.5, 650, 8, 34, 7, (0.067, 0.075, 0.082))
add_box('front_detail', 'front_license_plate_bsn453_6_3_lr', -10, 121, 632, 8, 7, 36, (0.067, 0.075, 0.082))
add_box('front_detail', 'front_license_plate_bsn453_6_3_bottom', -10, 107.5, 617.5, 8, 34, 7, (0.067, 0.075, 0.082))
add_box('front_detail', 'front_bumper_left_end_cap', 40, -780, 525, 150, 115, 130, (0.722, 0.722, 0.722))
add_box('front_detail', 'front_bumper_right_end_cap', 40, 780, 525, 150, 115, 130, (0.722, 0.722, 0.722))
add_box('body', 'hood_center_raised_rib', 320, 0, 1277, 760, 180, 48, (0.812, 0.776, 0.667))
add_box('body', 'hood_left_outer_rib', 330, -470, 1265, 730, 52, 38, (0.812, 0.776, 0.667))
add_box('body', 'hood_right_outer_rib', 330, 470, 1265, 730, 52, 38, (0.812, 0.776, 0.667))
add_box('body', 'left_hood_latch', 810, -610, 1210, 88, 50, 58, (0.722, 0.722, 0.722))
add_box('body', 'left_cowl_vent_slot', 1020, -350, 1335, 150, 42, 26, (0.114, 0.114, 0.114))
add_box('body', 'left_windshield_outer_seal', 1122, -548, 1370, 30, 55, 470, (0.114, 0.114, 0.114))
add_box('body', 'right_hood_latch', 810, 610, 1210, 88, 50, 58, (0.722, 0.722, 0.722))
add_box('body', 'right_cowl_vent_slot', 1020, 350, 1335, 150, 42, 26, (0.114, 0.114, 0.114))
add_box('body', 'right_windshield_outer_seal', 1122, 548, 1370, 30, 55, 470, (0.114, 0.114, 0.114))
add_box('body', 'windshield_top_seal', 1122, 0, 1798, 30, 1320, 45, (0.114, 0.114, 0.114))
add_box('body', 'windshield_bottom_seal', 1122, 0, 1360, 30, 1320, 42, (0.114, 0.114, 0.114))
add_box('hard_top', 'front_hardtop_roof_rib', 1290, 0, 1810, 45, 1510, 42, (0.945, 0.933, 0.894))
add_cylinder('hard_top', 'front_left_hardtop_vertical_frame', 1290, -765, 1450, 'z', 34, 640, (0.722, 0.722, 0.722))
add_cylinder('hard_top', 'front_right_hardtop_vertical_frame', 1290, 765, 1450, 'z', 34, 640, (0.722, 0.722, 0.722))
add_box('hard_top', 'middle_hardtop_roof_rib', 1960, 0, 1810, 45, 1510, 42, (0.945, 0.933, 0.894))
add_cylinder('hard_top', 'middle_left_hardtop_vertical_frame', 1960, -765, 1450, 'z', 34, 640, (0.722, 0.722, 0.722))
add_cylinder('hard_top', 'middle_right_hardtop_vertical_frame', 1960, 765, 1450, 'z', 34, 640, (0.722, 0.722, 0.722))
add_box('hard_top', 'rear_hardtop_roof_rib', 2640, 0, 1810, 45, 1510, 42, (0.945, 0.933, 0.894))
add_cylinder('hard_top', 'rear_left_hardtop_vertical_frame', 2640, -765, 1450, 'z', 34, 640, (0.722, 0.722, 0.722))
add_cylinder('hard_top', 'rear_right_hardtop_vertical_frame', 2640, 765, 1450, 'z', 34, 640, (0.722, 0.722, 0.722))
add_box('hard_top', 'tail_hardtop_roof_rib', 3300, 0, 1810, 45, 1510, 42, (0.945, 0.933, 0.894))
add_cylinder('hard_top', 'tail_left_hardtop_vertical_frame', 3300, -765, 1450, 'z', 34, 640, (0.722, 0.722, 0.722))
add_cylinder('hard_top', 'tail_right_hardtop_vertical_frame', 3300, 765, 1450, 'z', 34, 640, (0.722, 0.722, 0.722))
add_box('hard_top', 'left_hardtop_lower_retainer_rail', 1240, -830, 1288, 2200, 42, 46, (0.722, 0.722, 0.722))
add_box('hard_top', 'left_front_window_rubber_seal', 1420, -842, 1435, 535, 28, 355, (0.114, 0.114, 0.114))
add_mesh('hard_top', 'left_rear_window_rubber_seal', [(2528, -857, 1668), (2522.22, -857, 1704.46), (2505.46, -857, 1737.36), (2479.36, -857, 1763.46), (2446.46, -857, 1780.22), (2410, -857, 1786), (1933.54, -857, 1780.22), (1900.64, -857, 1763.46), (1874.54, -857, 1737.36), (1857.78, -857, 1704.46), (1852, -857, 1668), (1857.78, -857, 1485.54), (1874.54, -857, 1452.64), (1900.64, -857, 1426.54), (1933.54, -857, 1409.78), (1970, -857, 1404), (2446.46, -857, 1409.78), (2479.36, -857, 1426.54), (2505.46, -857, 1452.64), (2522.22, -857, 1485.54), (2528, -857, 1522), (2528, -827, 1668), (2522.22, -827, 1704.46), (2505.46, -827, 1737.36), (2479.36, -827, 1763.46), (2446.46, -827, 1780.22), (2410, -827, 1786), (1933.54, -827, 1780.22), (1900.64, -827, 1763.46), (1874.54, -827, 1737.36), (1857.78, -827, 1704.46), (1852, -827, 1668), (1857.78, -827, 1485.54), (1874.54, -827, 1452.64), (1900.64, -827, 1426.54), (1933.54, -827, 1409.78), (1970, -827, 1404), (2446.46, -827, 1409.78), (2479.36, -827, 1426.54), (2505.46, -827, 1452.64), (2522.22, -827, 1485.54), (2528, -827, 1522)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.114, 0.114, 0.114))
add_box('hard_top', 'left_hardtop_vertical_joint_1', 1320, -826, 1320, 22, 28, 570, (0.114, 0.114, 0.114))
add_box('hard_top', 'left_hardtop_vertical_joint_2', 1820, -826, 1320, 22, 28, 570, (0.114, 0.114, 0.114))
add_box('hard_top', 'left_hardtop_vertical_joint_3', 2500, -826, 1320, 22, 28, 570, (0.114, 0.114, 0.114))
add_box('hard_top', 'left_hardtop_vertical_joint_4', 3180, -826, 1320, 22, 28, 570, (0.114, 0.114, 0.114))
add_box('body', 'left_side_step_board', 1540, -865, 620, 1120, 210, 55, (0.945, 0.933, 0.894))
add_box('body', 'left_diesel_badge', 2925, -822, 980, 120, 24, 42, (0.722, 0.722, 0.722))
add_box('hard_top', 'right_hardtop_lower_retainer_rail', 1240, 830, 1288, 2200, 42, 46, (0.722, 0.722, 0.722))
add_box('hard_top', 'right_front_window_rubber_seal', 1420, 842, 1435, 535, 28, 355, (0.114, 0.114, 0.114))
add_mesh('hard_top', 'right_rear_window_rubber_seal', [(2528, 827, 1668), (2522.22, 827, 1704.46), (2505.46, 827, 1737.36), (2479.36, 827, 1763.46), (2446.46, 827, 1780.22), (2410, 827, 1786), (1933.54, 827, 1780.22), (1900.64, 827, 1763.46), (1874.54, 827, 1737.36), (1857.78, 827, 1704.46), (1852, 827, 1668), (1857.78, 827, 1485.54), (1874.54, 827, 1452.64), (1900.64, 827, 1426.54), (1933.54, 827, 1409.78), (1970, 827, 1404), (2446.46, 827, 1409.78), (2479.36, 827, 1426.54), (2505.46, 827, 1452.64), (2522.22, 827, 1485.54), (2528, 827, 1522), (2528, 857, 1668), (2522.22, 857, 1704.46), (2505.46, 857, 1737.36), (2479.36, 857, 1763.46), (2446.46, 857, 1780.22), (2410, 857, 1786), (1933.54, 857, 1780.22), (1900.64, 857, 1763.46), (1874.54, 857, 1737.36), (1857.78, 857, 1704.46), (1852, 857, 1668), (1857.78, 857, 1485.54), (1874.54, 857, 1452.64), (1900.64, 857, 1426.54), (1933.54, 857, 1409.78), (1970, 857, 1404), (2446.46, 857, 1409.78), (2479.36, 857, 1426.54), (2505.46, 857, 1452.64), (2522.22, 857, 1485.54), (2528, 857, 1522)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.114, 0.114, 0.114))
add_box('hard_top', 'right_hardtop_vertical_joint_1', 1320, 826, 1320, 22, 28, 570, (0.114, 0.114, 0.114))
add_box('hard_top', 'right_hardtop_vertical_joint_2', 1820, 826, 1320, 22, 28, 570, (0.114, 0.114, 0.114))
add_box('hard_top', 'right_hardtop_vertical_joint_3', 2500, 826, 1320, 22, 28, 570, (0.114, 0.114, 0.114))
add_box('hard_top', 'right_hardtop_vertical_joint_4', 3180, 826, 1320, 22, 28, 570, (0.114, 0.114, 0.114))
add_box('body', 'right_side_step_board', 1540, 865, 620, 1120, 210, 55, (0.945, 0.933, 0.894))
add_box('body', 'right_diesel_badge', 2925, 822, 980, 120, 24, 42, (0.722, 0.722, 0.722))
add_mesh('hard_top', 'rear_left_window_rubber_seal', [(3455, -50, 1677), (3455, -54.307, 1704.19), (3455, -66.8065, 1728.73), (3455, -86.2749, 1748.19), (3455, -110.807, 1760.69), (3455, -138, 1765), (3455, -389.193, 1760.69), (3455, -413.725, 1748.19), (3455, -433.193, 1728.73), (3455, -445.693, 1704.19), (3455, -450, 1677), (3455, -445.693, 1495.81), (3455, -433.193, 1471.27), (3455, -413.725, 1451.81), (3455, -389.193, 1439.31), (3455, -362, 1435), (3455, -110.807, 1439.31), (3455, -86.2749, 1451.81), (3455, -66.8065, 1471.27), (3455, -54.307, 1495.81), (3455, -50, 1523), (3485, -50, 1677), (3485, -54.307, 1704.19), (3485, -66.8065, 1728.73), (3485, -86.2749, 1748.19), (3485, -110.807, 1760.69), (3485, -138, 1765), (3485, -389.193, 1760.69), (3485, -413.725, 1748.19), (3485, -433.193, 1728.73), (3485, -445.693, 1704.19), (3485, -450, 1677), (3485, -445.693, 1495.81), (3485, -433.193, 1471.27), (3485, -413.725, 1451.81), (3485, -389.193, 1439.31), (3485, -362, 1435), (3485, -110.807, 1439.31), (3485, -86.2749, 1451.81), (3485, -66.8065, 1471.27), (3485, -54.307, 1495.81), (3485, -50, 1523)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.114, 0.114, 0.114))
add_mesh('hard_top', 'rear_right_window_rubber_seal', [(3455, 450, 1677), (3455, 445.693, 1704.19), (3455, 433.193, 1728.73), (3455, 413.725, 1748.19), (3455, 389.193, 1760.69), (3455, 362, 1765), (3455, 110.807, 1760.69), (3455, 86.2749, 1748.19), (3455, 66.8065, 1728.73), (3455, 54.307, 1704.19), (3455, 50, 1677), (3455, 54.307, 1495.81), (3455, 66.8065, 1471.27), (3455, 86.2749, 1451.81), (3455, 110.807, 1439.31), (3455, 138, 1435), (3455, 389.193, 1439.31), (3455, 413.725, 1451.81), (3455, 433.193, 1471.27), (3455, 445.693, 1495.81), (3455, 450, 1523), (3485, 450, 1677), (3485, 445.693, 1704.19), (3485, 433.193, 1728.73), (3485, 413.725, 1748.19), (3485, 389.193, 1760.69), (3485, 362, 1765), (3485, 110.807, 1760.69), (3485, 86.2749, 1748.19), (3485, 66.8065, 1728.73), (3485, 54.307, 1704.19), (3485, 50, 1677), (3485, 54.307, 1495.81), (3485, 66.8065, 1471.27), (3485, 86.2749, 1451.81), (3485, 110.807, 1439.31), (3485, 138, 1435), (3485, 389.193, 1439.31), (3485, 413.725, 1451.81), (3485, 433.193, 1471.27), (3485, 445.693, 1495.81), (3485, 450, 1523)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.114, 0.114, 0.114))
add_mesh('hard_top', 'rear_left_hardtop_window', [(3475, -80, 1667.5), (3475, -83.426, 1689.13), (3475, -93.3688, 1708.64), (3475, -108.855, 1724.13), (3475, -128.369, 1734.07), (3475, -150, 1737.5), (3475, -371.631, 1734.07), (3475, -391.145, 1724.13), (3475, -406.631, 1708.64), (3475, -416.574, 1689.13), (3475, -420, 1667.5), (3475, -416.574, 1510.87), (3475, -406.631, 1491.36), (3475, -391.145, 1475.87), (3475, -371.631, 1465.93), (3475, -350, 1462.5), (3475, -128.369, 1465.93), (3475, -108.855, 1475.87), (3475, -93.3688, 1491.36), (3475, -83.426, 1510.87), (3475, -80, 1532.5), (3495, -80, 1667.5), (3495, -83.426, 1689.13), (3495, -93.3688, 1708.64), (3495, -108.855, 1724.13), (3495, -128.369, 1734.07), (3495, -150, 1737.5), (3495, -371.631, 1734.07), (3495, -391.145, 1724.13), (3495, -406.631, 1708.64), (3495, -416.574, 1689.13), (3495, -420, 1667.5), (3495, -416.574, 1510.87), (3495, -406.631, 1491.36), (3495, -391.145, 1475.87), (3495, -371.631, 1465.93), (3495, -350, 1462.5), (3495, -128.369, 1465.93), (3495, -108.855, 1475.87), (3495, -93.3688, 1491.36), (3495, -83.426, 1510.87), (3495, -80, 1532.5)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.435, 0.647, 0.722))
add_mesh('hard_top', 'rear_right_hardtop_window', [(3475, 420, 1667.5), (3475, 416.574, 1689.13), (3475, 406.631, 1708.64), (3475, 391.145, 1724.13), (3475, 371.631, 1734.07), (3475, 350, 1737.5), (3475, 128.369, 1734.07), (3475, 108.855, 1724.13), (3475, 93.3688, 1708.64), (3475, 83.426, 1689.13), (3475, 80, 1667.5), (3475, 83.426, 1510.87), (3475, 93.3688, 1491.36), (3475, 108.855, 1475.87), (3475, 128.369, 1465.93), (3475, 150, 1462.5), (3475, 371.631, 1465.93), (3475, 391.145, 1475.87), (3475, 406.631, 1491.36), (3475, 416.574, 1510.87), (3475, 420, 1532.5), (3495, 420, 1667.5), (3495, 416.574, 1689.13), (3495, 406.631, 1708.64), (3495, 391.145, 1724.13), (3495, 371.631, 1734.07), (3495, 350, 1737.5), (3495, 128.369, 1734.07), (3495, 108.855, 1724.13), (3495, 93.3688, 1708.64), (3495, 83.426, 1689.13), (3495, 80, 1667.5), (3495, 83.426, 1510.87), (3495, 93.3688, 1491.36), (3495, 108.855, 1475.87), (3495, 128.369, 1465.93), (3495, 150, 1462.5), (3495, 371.631, 1465.93), (3495, 391.145, 1475.87), (3495, 406.631, 1491.36), (3495, 416.574, 1510.87), (3495, 420, 1532.5)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.435, 0.647, 0.722))
add_box('hard_top', 'rear_corner_glass_or_seal_45', 3500, -555, 1415, 28, 170, 300, (0.435, 0.647, 0.722))
add_box('hard_top', 'rear_corner_glass_or_seal_325', 3500, -275, 1415, 28, 170, 300, (0.435, 0.647, 0.722))
add_box('hard_top', 'rear_corner_glass_or_seal_875', 3500, 275, 1415, 28, 170, 300, (0.435, 0.647, 0.722))
add_box('hard_top', 'rear_corner_glass_or_seal_1155', 3500, 555, 1415, 28, 170, 300, (0.435, 0.647, 0.722))
add_box('front_detail', 'front_grille_black_mesh_horizontal_texture_1', 64, 0, 860, 18, 560, 12, (0.149, 0.220, 0.247))
add_box('front_detail', 'front_grille_black_mesh_horizontal_texture_2', 64, 0, 895, 18, 560, 12, (0.149, 0.220, 0.247))
add_box('front_detail', 'front_grille_black_mesh_horizontal_texture_3', 64, 0, 930, 18, 560, 12, (0.149, 0.220, 0.247))
add_box('front_detail', 'front_grille_black_mesh_horizontal_texture_4', 64, 0, 965, 18, 560, 12, (0.149, 0.220, 0.247))
add_box('front_detail', 'front_grille_black_mesh_vertical_texture_1', 62, -260, 852, 20, 12, 145, (0.149, 0.220, 0.247))
add_box('front_detail', 'front_grille_black_mesh_vertical_texture_2', 62, -170, 852, 20, 12, 145, (0.149, 0.220, 0.247))
add_box('front_detail', 'front_grille_black_mesh_vertical_texture_3', 62, -80, 852, 20, 12, 145, (0.149, 0.220, 0.247))
add_box('front_detail', 'front_grille_black_mesh_vertical_texture_4', 62, 80, 852, 20, 12, 145, (0.149, 0.220, 0.247))
add_box('front_detail', 'front_grille_black_mesh_vertical_texture_5', 62, 170, 852, 20, 12, 145, (0.149, 0.220, 0.247))
add_box('front_detail', 'front_grille_black_mesh_vertical_texture_6', 62, 260, 852, 20, 12, 145, (0.149, 0.220, 0.247))
add_cylinder('front_detail', 'grille_surround_screw_1', 58, -325, 812, 'x', 28, 20, (0.851, 0.835, 0.784))
add_cylinder('front_detail', 'grille_surround_screw_2', 58, -230, 1008, 'x', 28, 20, (0.851, 0.835, 0.784))
add_cylinder('front_detail', 'grille_surround_screw_3', 58, 230, 1008, 'x', 28, 20, (0.851, 0.835, 0.784))
add_cylinder('front_detail', 'grille_surround_screw_4', 58, 325, 812, 'x', 28, 20, (0.851, 0.835, 0.784))
add_box('front_detail', 'toyota_grille_letter_t_top', 52, -190, 940, 16, 58, 12, (0.839, 0.749, 0.278))
add_box('front_detail', 'toyota_grille_letter_t_stem', 52, -190, 895, 16, 13, 54, (0.839, 0.749, 0.278))
add_box('front_detail', 'toyota_grille_letter_o1_top', 52, -98, 938, 16, 52, 12, (0.839, 0.749, 0.278))
add_box('front_detail', 'toyota_grille_letter_o1_bottom', 52, -98, 893, 16, 52, 12, (0.839, 0.749, 0.278))
add_box('front_detail', 'toyota_grille_letter_o1_left', 52, -121, 900, 16, 11, 42, (0.839, 0.749, 0.278))
add_box('front_detail', 'toyota_grille_letter_o1_right', 52, -75, 900, 16, 11, 42, (0.839, 0.749, 0.278))
add_box('front_detail', 'toyota_grille_letter_o2_top', 52, 98, 938, 16, 52, 12, (0.839, 0.749, 0.278))
add_box('front_detail', 'toyota_grille_letter_o2_bottom', 52, 98, 893, 16, 52, 12, (0.839, 0.749, 0.278))
add_box('front_detail', 'toyota_grille_letter_o2_left', 52, 75, 900, 16, 11, 42, (0.839, 0.749, 0.278))
add_box('front_detail', 'toyota_grille_letter_o2_right', 52, 121, 900, 16, 11, 42, (0.839, 0.749, 0.278))
add_box('front_detail', 'toyota_grille_letter_y_left_upper', 52, -21, 928, 16, 18, 12, (0.839, 0.749, 0.278))
add_box('front_detail', 'toyota_grille_letter_y_right_upper', 52, 21, 928, 16, 18, 12, (0.839, 0.749, 0.278))
add_box('front_detail', 'toyota_grille_letter_y_stem', 52, 0, 895, 16, 12, 42, (0.839, 0.749, 0.278))
add_box('front_detail', 'toyota_grille_letter_a_left', 52, 184, 895, 16, 11, 55, (0.839, 0.749, 0.278))
add_box('front_detail', 'toyota_grille_letter_a_right', 52, 228, 895, 16, 11, 55, (0.839, 0.749, 0.278))
add_box('front_detail', 'toyota_grille_letter_a_top', 52, 206, 938, 16, 52, 12, (0.839, 0.749, 0.278))
add_box('front_detail', 'toyota_grille_letter_a_bar', 52, 206, 915, 16, 42, 10, (0.839, 0.749, 0.278))
add_box('front_detail', 'left_front_fender_turn_signal_base', 290, -642, 1058, 155, 80, 24, (0.851, 0.835, 0.784))
add_cylinder('front_detail', 'left_front_fender_turn_signal_lens', 298, -642, 1075, 'z', 78, 32, (0.851, 0.471, 0.141))
add_cylinder('front_detail', 'left_headlamp_glass_highlight', 64, -445, 1035, 'x', 126, 18, (0.894, 0.863, 0.780))
add_cylinder('front_detail', 'left_headlamp_mount_screw_upper', 58, -375, 1094, 'x', 22, 18, (0.851, 0.835, 0.784))
add_cylinder('front_detail', 'left_headlamp_mount_screw_lower', 58, -515, 876, 'x', 22, 18, (0.851, 0.835, 0.784))
add_box('body', 'left_front_quarter_louver_slot_1', 885, -826, 890, 175, 24, 14, (0.149, 0.220, 0.247))
add_box('body', 'left_front_quarter_louver_highlight_1', 880, -812, 906, 160, 16, 8, (0.894, 0.863, 0.780))
add_box('body', 'left_front_quarter_louver_slot_2', 885, -826, 925, 175, 24, 14, (0.149, 0.220, 0.247))
add_box('body', 'left_front_quarter_louver_highlight_2', 880, -812, 941, 160, 16, 8, (0.894, 0.863, 0.780))
add_box('body', 'left_front_quarter_louver_slot_3', 885, -826, 960, 175, 24, 14, (0.149, 0.220, 0.247))
add_box('body', 'left_front_quarter_louver_highlight_3', 880, -812, 976, 160, 16, 8, (0.894, 0.863, 0.780))
add_box('body', 'left_front_quarter_louver_slot_4', 885, -826, 995, 175, 24, 14, (0.149, 0.220, 0.247))
add_box('body', 'left_front_quarter_louver_highlight_4', 880, -812, 1011, 160, 16, 8, (0.894, 0.863, 0.780))
add_box('body', 'left_front_quarter_louver_slot_5', 885, -826, 1030, 175, 24, 14, (0.149, 0.220, 0.247))
add_box('body', 'left_front_quarter_louver_highlight_5', 880, -812, 1046, 160, 16, 8, (0.894, 0.863, 0.780))
add_box('body', 'left_beltline_trim_front_door', 1140, -834, 1118, 780, 22, 28, (0.851, 0.835, 0.784))
add_box('body', 'left_beltline_trim_rear_tub', 1965, -834, 1118, 1390, 22, 28, (0.851, 0.835, 0.784))
add_box('body', 'left_door_outer_skin_upper_pressing', 1235, -789, 1040, 725, 34, 70, (0.616, 0.588, 0.494))
add_box('body', 'left_door_skin_lower_recess_shadow', 1235, -789, 885, 725, 32, 76, (0.616, 0.588, 0.494))
add_box('body', 'left_door_window_front_vertical_frame', 1115, -812, 1192, 34, 35, 385, (0.067, 0.075, 0.082))
add_box('body', 'left_door_window_rear_vertical_frame', 1642, -812, 1192, 34, 35, 385, (0.067, 0.075, 0.082))
add_box('body', 'left_door_window_top_frame', 1115, -812, 1546, 560, 35, 34, (0.067, 0.075, 0.082))
add_box('body', 'left_door_window_bottom_frame', 1115, -812, 1186, 560, 35, 30, (0.067, 0.075, 0.082))
add_cylinder('body', 'left_door_lock_cylinder', 1645, -835, 1032, 'y', 36, 22, (0.851, 0.835, 0.784))
add_cylinder('body', 'left_door_hinge_pin_cap_1', 1126, -843, 820, 'y', 32, 26, (0.851, 0.835, 0.784))
add_cylinder('body', 'left_door_hinge_pin_cap_2', 1126, -843, 930, 'y', 32, 26, (0.851, 0.835, 0.784))
add_cylinder('body', 'left_door_hinge_pin_cap_3', 1126, -843, 1180, 'y', 32, 26, (0.851, 0.835, 0.784))
add_cylinder('body', 'left_door_hinge_pin_cap_4', 1126, -843, 1290, 'y', 32, 26, (0.851, 0.835, 0.784))
add_box('hard_top', 'left_hardtop_front_window_upper_inner_shadow', 1420, -854, 1732, 500, 18, 22, (0.149, 0.220, 0.247))
add_box('hard_top', 'left_hardtop_front_window_lower_inner_shadow', 1420, -854, 1360, 500, 18, 22, (0.149, 0.220, 0.247))
add_box('hard_top', 'left_hardtop_front_window_sliding_mullion', 1510, -858, 1438, 28, 24, 300, (0.067, 0.075, 0.082))
add_cylinder('hard_top', 'left_hardtop_front_window_rounded_corner_1', 1170, -862, 1360, 'y', 54, 24, (0.114, 0.114, 0.114))
add_cylinder('hard_top', 'left_hardtop_front_window_rounded_corner_2', 1670, -862, 1360, 'y', 54, 24, (0.114, 0.114, 0.114))
add_cylinder('hard_top', 'left_hardtop_front_window_rounded_corner_3', 1170, -862, 1680, 'y', 54, 24, (0.114, 0.114, 0.114))
add_cylinder('hard_top', 'left_hardtop_front_window_rounded_corner_4', 1670, -862, 1680, 'y', 54, 24, (0.114, 0.114, 0.114))
add_box('hard_top', 'left_hardtop_rear_window_upper_inner_shadow', 2190, -854, 1732, 610, 18, 22, (0.149, 0.220, 0.247))
add_box('hard_top', 'left_hardtop_rear_window_lower_inner_shadow', 2190, -854, 1360, 610, 18, 22, (0.149, 0.220, 0.247))
add_box('hard_top', 'left_hardtop_rear_window_sliding_mullion', 2299.8, -858, 1438, 28, 24, 300, (0.067, 0.075, 0.082))
add_cylinder('hard_top', 'left_hardtop_rear_window_rounded_corner_1', 1885, -862, 1360, 'y', 54, 24, (0.114, 0.114, 0.114))
add_cylinder('hard_top', 'left_hardtop_rear_window_rounded_corner_2', 2495, -862, 1360, 'y', 54, 24, (0.114, 0.114, 0.114))
add_cylinder('hard_top', 'left_hardtop_rear_window_rounded_corner_3', 1885, -862, 1680, 'y', 54, 24, (0.114, 0.114, 0.114))
add_cylinder('hard_top', 'left_hardtop_rear_window_rounded_corner_4', 2495, -862, 1680, 'y', 54, 24, (0.114, 0.114, 0.114))
add_mesh('hard_top', 'left_classic_rear_quarter_window_dark_inner_inset', [(2464, -874, 1651), (2460.38, -874, 1673.87), (2449.87, -874, 1694.5), (2433.5, -874, 1710.87), (2412.87, -874, 1721.38), (2390, -874, 1725), (1967.13, -874, 1721.38), (1946.5, -874, 1710.87), (1930.13, -874, 1694.5), (1919.62, -874, 1673.87), (1916, -874, 1651), (1919.62, -874, 1516.13), (1930.13, -874, 1495.5), (1946.5, -874, 1479.13), (1967.13, -874, 1468.62), (1990, -874, 1465), (2412.87, -874, 1468.62), (2433.5, -874, 1479.13), (2449.87, -874, 1495.5), (2460.38, -874, 1516.13), (2464, -874, 1539), (2464, -858, 1651), (2460.38, -858, 1673.87), (2449.87, -858, 1694.5), (2433.5, -858, 1710.87), (2412.87, -858, 1721.38), (2390, -858, 1725), (1967.13, -858, 1721.38), (1946.5, -858, 1710.87), (1930.13, -858, 1694.5), (1919.62, -858, 1673.87), (1916, -858, 1651), (1919.62, -858, 1516.13), (1930.13, -858, 1495.5), (1946.5, -858, 1479.13), (1967.13, -858, 1468.62), (1990, -858, 1465), (2412.87, -858, 1468.62), (2433.5, -858, 1479.13), (2449.87, -858, 1495.5), (2460.38, -858, 1516.13), (2464, -858, 1539)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.149, 0.220, 0.247))
add_box('hard_top', 'left_classic_rear_quarter_window_upper_glare_arc', 2190, -876, 1695, 440, 16, 18, (0.894, 0.863, 0.780))
add_box('hard_top', 'left_classic_rear_quarter_window_lower_shadow_arc', 2190, -878, 1488, 470, 16, 16, (0.149, 0.220, 0.247))
add_box('hard_top', 'left_roof_drip_rail_outer_shadow', 1235, -862, 1784, 2275, 28, 30, (0.616, 0.588, 0.494))
add_box('hard_top', 'left_roof_side_panel_subtle_vertical_pressing_1', 1420, -804, 1325, 20, 18, 520, (0.616, 0.588, 0.494))
add_box('hard_top', 'left_roof_side_panel_subtle_vertical_pressing_2', 1840, -804, 1325, 20, 18, 520, (0.616, 0.588, 0.494))
add_box('hard_top', 'left_roof_side_panel_subtle_vertical_pressing_3', 2260, -804, 1325, 20, 18, 520, (0.616, 0.588, 0.494))
add_box('hard_top', 'left_roof_side_panel_subtle_vertical_pressing_4', 2680, -804, 1325, 20, 18, 520, (0.616, 0.588, 0.494))
add_box('hard_top', 'left_roof_side_panel_subtle_vertical_pressing_5', 3100, -804, 1325, 20, 18, 520, (0.616, 0.588, 0.494))
add_box('body', 'left_front_black_fender_flare_arc_1', 1046.32, -823, 548.746, 68, 46, 34, (0.067, 0.075, 0.082))
add_box('body', 'left_front_black_fender_flare_arc_2', 998.868, -823, 627.72, 68, 46, 34, (0.067, 0.075, 0.082))
add_box('body', 'left_front_black_fender_flare_arc_3', 933.72, -823, 692.868, 68, 46, 34, (0.067, 0.075, 0.082))
add_box('body', 'left_front_black_fender_flare_arc_4', 854.746, -823, 740.32, 68, 46, 34, (0.067, 0.075, 0.082))
add_box('body', 'left_front_black_fender_flare_arc_5', 766.639, -823, 767.257, 68, 46, 34, (0.067, 0.075, 0.082))
add_box('body', 'left_front_black_fender_flare_arc_6', 674.632, -823, 772.079, 68, 46, 34, (0.067, 0.075, 0.082))
add_box('body', 'left_front_black_fender_flare_arc_7', 584.192, -823, 754.499, 68, 46, 34, (0.067, 0.075, 0.082))
add_box('body', 'left_front_black_fender_flare_arc_8', 500.691, -823, 715.562, 68, 46, 34, (0.067, 0.075, 0.082))
add_box('body', 'left_front_black_fender_flare_arc_9', 429.09, -823, 657.581, 68, 46, 34, (0.067, 0.075, 0.082))
add_box('body', 'left_front_black_fender_flare_arc_10', 373.642, -823, 584, 68, 46, 34, (0.067, 0.075, 0.082))
add_box('body', 'left_rear_black_fender_flare_arc_1', 3319.44, -823, 543.459, 68, 46, 34, (0.067, 0.075, 0.082))
add_box('body', 'left_rear_black_fender_flare_arc_2', 3273.62, -823, 619.716, 68, 46, 34, (0.067, 0.075, 0.082))
add_box('body', 'left_rear_black_fender_flare_arc_3', 3210.72, -823, 682.624, 68, 46, 34, (0.067, 0.075, 0.082))
add_box('body', 'left_rear_black_fender_flare_arc_4', 3134.46, -823, 728.444, 68, 46, 34, (0.067, 0.075, 0.082))
add_box('body', 'left_rear_black_fender_flare_arc_5', 3049.38, -823, 754.455, 68, 46, 34, (0.067, 0.075, 0.082))
add_box('body', 'left_rear_black_fender_flare_arc_6', 2960.54, -823, 759.111, 68, 46, 34, (0.067, 0.075, 0.082))
add_box('body', 'left_rear_black_fender_flare_arc_7', 2873.21, -823, 742.136, 68, 46, 34, (0.067, 0.075, 0.082))
add_box('body', 'left_rear_black_fender_flare_arc_8', 2792.58, -823, 704.538, 68, 46, 34, (0.067, 0.075, 0.082))
add_box('body', 'left_rear_black_fender_flare_arc_9', 2723.44, -823, 648.55, 68, 46, 34, (0.067, 0.075, 0.082))
add_box('body', 'left_rear_black_fender_flare_arc_10', 2669.9, -823, 577.5, 68, 46, 34, (0.067, 0.075, 0.082))
add_box('body', 'left_side_step_tread_strip_1', 1120, -872, 674, 130, 162, 12, (0.851, 0.835, 0.784))
add_box('body', 'left_side_step_tread_strip_2', 1320, -872, 674, 130, 162, 12, (0.851, 0.835, 0.784))
add_box('body', 'left_side_step_tread_strip_3', 1520, -872, 674, 130, 162, 12, (0.851, 0.835, 0.784))
add_box('body', 'left_side_step_tread_strip_4', 1720, -872, 674, 130, 162, 12, (0.851, 0.835, 0.784))
add_box('body', 'left_side_step_tread_strip_5', 1920, -872, 674, 130, 162, 12, (0.851, 0.835, 0.784))
add_box('body', 'left_side_step_drop_bracket_1', 1180, -760, 530, 52, 38, 155, (0.176, 0.188, 0.200))
add_box('body', 'left_side_step_drop_bracket_2', 1540, -760, 530, 52, 38, 155, (0.176, 0.188, 0.200))
add_box('body', 'left_side_step_drop_bracket_3', 1900, -760, 530, 52, 38, 155, (0.176, 0.188, 0.200))
add_box('body', 'left_front_mud_flap', 420, -780, 190, 42, 135, 280, (0.114, 0.114, 0.114))
add_box('body', 'left_rear_mud_flap', 3350, -780, 185, 42, 135, 300, (0.114, 0.114, 0.114))
add_box('front_detail', 'right_front_fender_turn_signal_base', 290, 642, 1058, 155, 80, 24, (0.851, 0.835, 0.784))
add_cylinder('front_detail', 'right_front_fender_turn_signal_lens', 298, 642, 1075, 'z', 78, 32, (0.851, 0.471, 0.141))
add_cylinder('front_detail', 'right_headlamp_glass_highlight', 64, 445, 1035, 'x', 126, 18, (0.894, 0.863, 0.780))
add_cylinder('front_detail', 'right_headlamp_mount_screw_upper', 58, 375, 1094, 'x', 22, 18, (0.851, 0.835, 0.784))
add_cylinder('front_detail', 'right_headlamp_mount_screw_lower', 58, 515, 876, 'x', 22, 18, (0.851, 0.835, 0.784))
add_box('body', 'right_front_quarter_louver_slot_1', 885, 826, 890, 175, 24, 14, (0.149, 0.220, 0.247))
add_box('body', 'right_front_quarter_louver_highlight_1', 880, 812, 906, 160, 16, 8, (0.894, 0.863, 0.780))
add_box('body', 'right_front_quarter_louver_slot_2', 885, 826, 925, 175, 24, 14, (0.149, 0.220, 0.247))
add_box('body', 'right_front_quarter_louver_highlight_2', 880, 812, 941, 160, 16, 8, (0.894, 0.863, 0.780))
add_box('body', 'right_front_quarter_louver_slot_3', 885, 826, 960, 175, 24, 14, (0.149, 0.220, 0.247))
add_box('body', 'right_front_quarter_louver_highlight_3', 880, 812, 976, 160, 16, 8, (0.894, 0.863, 0.780))
add_box('body', 'right_front_quarter_louver_slot_4', 885, 826, 995, 175, 24, 14, (0.149, 0.220, 0.247))
add_box('body', 'right_front_quarter_louver_highlight_4', 880, 812, 1011, 160, 16, 8, (0.894, 0.863, 0.780))
add_box('body', 'right_front_quarter_louver_slot_5', 885, 826, 1030, 175, 24, 14, (0.149, 0.220, 0.247))
add_box('body', 'right_front_quarter_louver_highlight_5', 880, 812, 1046, 160, 16, 8, (0.894, 0.863, 0.780))
add_box('body', 'right_beltline_trim_front_door', 1140, 834, 1118, 780, 22, 28, (0.851, 0.835, 0.784))
add_box('body', 'right_beltline_trim_rear_tub', 1965, 834, 1118, 1390, 22, 28, (0.851, 0.835, 0.784))
add_box('body', 'right_door_outer_skin_upper_pressing', 1235, 789, 1040, 725, 34, 70, (0.616, 0.588, 0.494))
add_box('body', 'right_door_skin_lower_recess_shadow', 1235, 789, 885, 725, 32, 76, (0.616, 0.588, 0.494))
add_box('body', 'right_door_window_front_vertical_frame', 1115, 812, 1192, 34, 35, 385, (0.067, 0.075, 0.082))
add_box('body', 'right_door_window_rear_vertical_frame', 1642, 812, 1192, 34, 35, 385, (0.067, 0.075, 0.082))
add_box('body', 'right_door_window_top_frame', 1115, 812, 1546, 560, 35, 34, (0.067, 0.075, 0.082))
add_box('body', 'right_door_window_bottom_frame', 1115, 812, 1186, 560, 35, 30, (0.067, 0.075, 0.082))
add_cylinder('body', 'right_door_lock_cylinder', 1645, 835, 1032, 'y', 36, 22, (0.851, 0.835, 0.784))
add_cylinder('body', 'right_door_hinge_pin_cap_1', 1126, 843, 820, 'y', 32, 26, (0.851, 0.835, 0.784))
add_cylinder('body', 'right_door_hinge_pin_cap_2', 1126, 843, 930, 'y', 32, 26, (0.851, 0.835, 0.784))
add_cylinder('body', 'right_door_hinge_pin_cap_3', 1126, 843, 1180, 'y', 32, 26, (0.851, 0.835, 0.784))
add_cylinder('body', 'right_door_hinge_pin_cap_4', 1126, 843, 1290, 'y', 32, 26, (0.851, 0.835, 0.784))
add_box('hard_top', 'right_hardtop_front_window_upper_inner_shadow', 1420, 854, 1732, 500, 18, 22, (0.149, 0.220, 0.247))
add_box('hard_top', 'right_hardtop_front_window_lower_inner_shadow', 1420, 854, 1360, 500, 18, 22, (0.149, 0.220, 0.247))
add_box('hard_top', 'right_hardtop_front_window_sliding_mullion', 1510, 858, 1438, 28, 24, 300, (0.067, 0.075, 0.082))
add_cylinder('hard_top', 'right_hardtop_front_window_rounded_corner_1', 1170, 862, 1360, 'y', 54, 24, (0.114, 0.114, 0.114))
add_cylinder('hard_top', 'right_hardtop_front_window_rounded_corner_2', 1670, 862, 1360, 'y', 54, 24, (0.114, 0.114, 0.114))
add_cylinder('hard_top', 'right_hardtop_front_window_rounded_corner_3', 1170, 862, 1680, 'y', 54, 24, (0.114, 0.114, 0.114))
add_cylinder('hard_top', 'right_hardtop_front_window_rounded_corner_4', 1670, 862, 1680, 'y', 54, 24, (0.114, 0.114, 0.114))
add_box('hard_top', 'right_hardtop_rear_window_upper_inner_shadow', 2190, 854, 1732, 610, 18, 22, (0.149, 0.220, 0.247))
add_box('hard_top', 'right_hardtop_rear_window_lower_inner_shadow', 2190, 854, 1360, 610, 18, 22, (0.149, 0.220, 0.247))
add_box('hard_top', 'right_hardtop_rear_window_sliding_mullion', 2299.8, 858, 1438, 28, 24, 300, (0.067, 0.075, 0.082))
add_cylinder('hard_top', 'right_hardtop_rear_window_rounded_corner_1', 1885, 862, 1360, 'y', 54, 24, (0.114, 0.114, 0.114))
add_cylinder('hard_top', 'right_hardtop_rear_window_rounded_corner_2', 2495, 862, 1360, 'y', 54, 24, (0.114, 0.114, 0.114))
add_cylinder('hard_top', 'right_hardtop_rear_window_rounded_corner_3', 1885, 862, 1680, 'y', 54, 24, (0.114, 0.114, 0.114))
add_cylinder('hard_top', 'right_hardtop_rear_window_rounded_corner_4', 2495, 862, 1680, 'y', 54, 24, (0.114, 0.114, 0.114))
add_mesh('hard_top', 'right_classic_rear_quarter_window_dark_inner_inset', [(2464, 858, 1651), (2460.38, 858, 1673.87), (2449.87, 858, 1694.5), (2433.5, 858, 1710.87), (2412.87, 858, 1721.38), (2390, 858, 1725), (1967.13, 858, 1721.38), (1946.5, 858, 1710.87), (1930.13, 858, 1694.5), (1919.62, 858, 1673.87), (1916, 858, 1651), (1919.62, 858, 1516.13), (1930.13, 858, 1495.5), (1946.5, 858, 1479.13), (1967.13, 858, 1468.62), (1990, 858, 1465), (2412.87, 858, 1468.62), (2433.5, 858, 1479.13), (2449.87, 858, 1495.5), (2460.38, 858, 1516.13), (2464, 858, 1539), (2464, 874, 1651), (2460.38, 874, 1673.87), (2449.87, 874, 1694.5), (2433.5, 874, 1710.87), (2412.87, 874, 1721.38), (2390, 874, 1725), (1967.13, 874, 1721.38), (1946.5, 874, 1710.87), (1930.13, 874, 1694.5), (1919.62, 874, 1673.87), (1916, 874, 1651), (1919.62, 874, 1516.13), (1930.13, 874, 1495.5), (1946.5, 874, 1479.13), (1967.13, 874, 1468.62), (1990, 874, 1465), (2412.87, 874, 1468.62), (2433.5, 874, 1479.13), (2449.87, 874, 1495.5), (2460.38, 874, 1516.13), (2464, 874, 1539)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.149, 0.220, 0.247))
add_box('hard_top', 'right_classic_rear_quarter_window_upper_glare_arc', 2190, 876, 1695, 440, 16, 18, (0.894, 0.863, 0.780))
add_box('hard_top', 'right_classic_rear_quarter_window_lower_shadow_arc', 2190, 878, 1488, 470, 16, 16, (0.149, 0.220, 0.247))
add_box('hard_top', 'right_roof_drip_rail_outer_shadow', 1235, 862, 1784, 2275, 28, 30, (0.616, 0.588, 0.494))
add_box('hard_top', 'right_roof_side_panel_subtle_vertical_pressing_1', 1420, 804, 1325, 20, 18, 520, (0.616, 0.588, 0.494))
add_box('hard_top', 'right_roof_side_panel_subtle_vertical_pressing_2', 1840, 804, 1325, 20, 18, 520, (0.616, 0.588, 0.494))
add_box('hard_top', 'right_roof_side_panel_subtle_vertical_pressing_3', 2260, 804, 1325, 20, 18, 520, (0.616, 0.588, 0.494))
add_box('hard_top', 'right_roof_side_panel_subtle_vertical_pressing_4', 2680, 804, 1325, 20, 18, 520, (0.616, 0.588, 0.494))
add_box('hard_top', 'right_roof_side_panel_subtle_vertical_pressing_5', 3100, 804, 1325, 20, 18, 520, (0.616, 0.588, 0.494))
add_box('body', 'right_front_black_fender_flare_arc_1', 1046.32, 823, 548.746, 68, 46, 34, (0.067, 0.075, 0.082))
add_box('body', 'right_front_black_fender_flare_arc_2', 998.868, 823, 627.72, 68, 46, 34, (0.067, 0.075, 0.082))
add_box('body', 'right_front_black_fender_flare_arc_3', 933.72, 823, 692.868, 68, 46, 34, (0.067, 0.075, 0.082))
add_box('body', 'right_front_black_fender_flare_arc_4', 854.746, 823, 740.32, 68, 46, 34, (0.067, 0.075, 0.082))
add_box('body', 'right_front_black_fender_flare_arc_5', 766.639, 823, 767.257, 68, 46, 34, (0.067, 0.075, 0.082))
add_box('body', 'right_front_black_fender_flare_arc_6', 674.632, 823, 772.079, 68, 46, 34, (0.067, 0.075, 0.082))
add_box('body', 'right_front_black_fender_flare_arc_7', 584.192, 823, 754.499, 68, 46, 34, (0.067, 0.075, 0.082))
add_box('body', 'right_front_black_fender_flare_arc_8', 500.691, 823, 715.562, 68, 46, 34, (0.067, 0.075, 0.082))
add_box('body', 'right_front_black_fender_flare_arc_9', 429.09, 823, 657.581, 68, 46, 34, (0.067, 0.075, 0.082))
add_box('body', 'right_front_black_fender_flare_arc_10', 373.642, 823, 584, 68, 46, 34, (0.067, 0.075, 0.082))
add_box('body', 'right_rear_black_fender_flare_arc_1', 3319.44, 823, 543.459, 68, 46, 34, (0.067, 0.075, 0.082))
add_box('body', 'right_rear_black_fender_flare_arc_2', 3273.62, 823, 619.716, 68, 46, 34, (0.067, 0.075, 0.082))
add_box('body', 'right_rear_black_fender_flare_arc_3', 3210.72, 823, 682.624, 68, 46, 34, (0.067, 0.075, 0.082))
add_box('body', 'right_rear_black_fender_flare_arc_4', 3134.46, 823, 728.444, 68, 46, 34, (0.067, 0.075, 0.082))
add_box('body', 'right_rear_black_fender_flare_arc_5', 3049.38, 823, 754.455, 68, 46, 34, (0.067, 0.075, 0.082))
add_box('body', 'right_rear_black_fender_flare_arc_6', 2960.54, 823, 759.111, 68, 46, 34, (0.067, 0.075, 0.082))
add_box('body', 'right_rear_black_fender_flare_arc_7', 2873.21, 823, 742.136, 68, 46, 34, (0.067, 0.075, 0.082))
add_box('body', 'right_rear_black_fender_flare_arc_8', 2792.58, 823, 704.538, 68, 46, 34, (0.067, 0.075, 0.082))
add_box('body', 'right_rear_black_fender_flare_arc_9', 2723.44, 823, 648.55, 68, 46, 34, (0.067, 0.075, 0.082))
add_box('body', 'right_rear_black_fender_flare_arc_10', 2669.9, 823, 577.5, 68, 46, 34, (0.067, 0.075, 0.082))
add_box('body', 'right_side_step_tread_strip_1', 1120, 872, 674, 130, 162, 12, (0.851, 0.835, 0.784))
add_box('body', 'right_side_step_tread_strip_2', 1320, 872, 674, 130, 162, 12, (0.851, 0.835, 0.784))
add_box('body', 'right_side_step_tread_strip_3', 1520, 872, 674, 130, 162, 12, (0.851, 0.835, 0.784))
add_box('body', 'right_side_step_tread_strip_4', 1720, 872, 674, 130, 162, 12, (0.851, 0.835, 0.784))
add_box('body', 'right_side_step_tread_strip_5', 1920, 872, 674, 130, 162, 12, (0.851, 0.835, 0.784))
add_box('body', 'right_side_step_drop_bracket_1', 1180, 760, 530, 52, 38, 155, (0.176, 0.188, 0.200))
add_box('body', 'right_side_step_drop_bracket_2', 1540, 760, 530, 52, 38, 155, (0.176, 0.188, 0.200))
add_box('body', 'right_side_step_drop_bracket_3', 1900, 760, 530, 52, 38, 155, (0.176, 0.188, 0.200))
add_box('body', 'right_front_mud_flap', 420, 780, 190, 42, 135, 280, (0.114, 0.114, 0.114))
add_box('body', 'right_rear_mud_flap', 3350, 780, 185, 42, 135, 300, (0.114, 0.114, 0.114))
add_box('hard_top', 'rear_split_door_center_seal', 3505, 0, 1180, 30, 36, 650, (0.114, 0.114, 0.114))
add_mesh('hard_top', 'rear_door_left_glass_dark_inset', [(3491, -107.5, 1654.5), (3491, -110.339, 1672.42), (3491, -118.577, 1688.59), (3491, -131.408, 1701.42), (3491, -147.577, 1709.66), (3491, -165.5, 1712.5), (3491, -352.423, 1709.66), (3491, -368.592, 1701.42), (3491, -381.423, 1688.59), (3491, -389.661, 1672.42), (3491, -392.5, 1654.5), (3491, -389.661, 1527.58), (3491, -381.423, 1511.41), (3491, -368.592, 1498.58), (3491, -352.423, 1490.34), (3491, -334.5, 1487.5), (3491, -147.577, 1490.34), (3491, -131.408, 1498.58), (3491, -118.577, 1511.41), (3491, -110.339, 1527.58), (3491, -107.5, 1545.5), (3513, -107.5, 1654.5), (3513, -110.339, 1672.42), (3513, -118.577, 1688.59), (3513, -131.408, 1701.42), (3513, -147.577, 1709.66), (3513, -165.5, 1712.5), (3513, -352.423, 1709.66), (3513, -368.592, 1701.42), (3513, -381.423, 1688.59), (3513, -389.661, 1672.42), (3513, -392.5, 1654.5), (3513, -389.661, 1527.58), (3513, -381.423, 1511.41), (3513, -368.592, 1498.58), (3513, -352.423, 1490.34), (3513, -334.5, 1487.5), (3513, -147.577, 1490.34), (3513, -131.408, 1498.58), (3513, -118.577, 1511.41), (3513, -110.339, 1527.58), (3513, -107.5, 1545.5)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.149, 0.220, 0.247))
add_mesh('hard_top', 'rear_door_right_glass_dark_inset', [(3491, 392.5, 1654.5), (3491, 389.661, 1672.42), (3491, 381.423, 1688.59), (3491, 368.592, 1701.42), (3491, 352.423, 1709.66), (3491, 334.5, 1712.5), (3491, 147.577, 1709.66), (3491, 131.408, 1701.42), (3491, 118.577, 1688.59), (3491, 110.339, 1672.42), (3491, 107.5, 1654.5), (3491, 110.339, 1527.58), (3491, 118.577, 1511.41), (3491, 131.408, 1498.58), (3491, 147.577, 1490.34), (3491, 165.5, 1487.5), (3491, 352.423, 1490.34), (3491, 368.592, 1498.58), (3491, 381.423, 1511.41), (3491, 389.661, 1527.58), (3491, 392.5, 1545.5), (3513, 392.5, 1654.5), (3513, 389.661, 1672.42), (3513, 381.423, 1688.59), (3513, 368.592, 1701.42), (3513, 352.423, 1709.66), (3513, 334.5, 1712.5), (3513, 147.577, 1709.66), (3513, 131.408, 1701.42), (3513, 118.577, 1688.59), (3513, 110.339, 1672.42), (3513, 107.5, 1654.5), (3513, 110.339, 1527.58), (3513, 118.577, 1511.41), (3513, 131.408, 1498.58), (3513, 147.577, 1490.34), (3513, 165.5, 1487.5), (3513, 352.423, 1490.34), (3513, 368.592, 1498.58), (3513, 381.423, 1511.41), (3513, 389.661, 1527.58), (3513, 392.5, 1545.5)], [(0, 1, 2, 3, 4, 5, 6, 7, 8, 9, 10, 11, 12, 13, 14, 15, 16, 17, 18, 19, 20), (41, 40, 39, 38, 37, 36, 35, 34, 33, 32, 31, 30, 29, 28, 27, 26, 25, 24, 23, 22, 21), (0, 1, 22, 21), (1, 2, 23, 22), (2, 3, 24, 23), (3, 4, 25, 24), (4, 5, 26, 25), (5, 6, 27, 26), (6, 7, 28, 27), (7, 8, 29, 28), (8, 9, 30, 29), (9, 10, 31, 30), (10, 11, 32, 31), (11, 12, 33, 32), (12, 13, 34, 33), (13, 14, 35, 34), (14, 15, 36, 35), (15, 16, 37, 36), (16, 17, 38, 37), (17, 18, 39, 38), (18, 19, 40, 39), (19, 20, 41, 40), (20, 0, 21, 41)], (0.149, 0.220, 0.247))
add_box('hard_top', 'rear_door_window_center_mullion', 3496, 0, 1462, 34, 34, 304, (0.067, 0.075, 0.082))
add_cylinder('hard_top', 'rear_left_door_hinge_barrel_1', 3520, -650, 1180, 'z', 42, 165, (0.851, 0.835, 0.784))
add_cylinder('hard_top', 'rear_left_door_hinge_barrel_2', 3520, -650, 1510, 'z', 42, 165, (0.851, 0.835, 0.784))
add_box('hard_top', 'rear_left_door_pull_handle', 3526, -110, 1205, 28, 120, 44, (0.851, 0.835, 0.784))
add_cylinder('hard_top', 'rear_left_door_lock_button', 3536, -190, 1190, 'x', 38, 22, (0.851, 0.835, 0.784))
add_cylinder('hard_top', 'rear_right_door_hinge_barrel_1', 3520, 650, 1180, 'z', 42, 165, (0.851, 0.835, 0.784))
add_cylinder('hard_top', 'rear_right_door_hinge_barrel_2', 3520, 650, 1510, 'z', 42, 165, (0.851, 0.835, 0.784))
add_box('hard_top', 'rear_right_door_pull_handle', 3526, 110, 1205, 28, 120, 44, (0.851, 0.835, 0.784))
add_cylinder('hard_top', 'rear_right_door_lock_button', 3536, 190, 1190, 'x', 38, 22, (0.851, 0.835, 0.784))
add_cylinder('body', 'rear_spare_sidewall_highlight_ring', 3628, 0, 1020, 'x', 585, 18, (0.616, 0.588, 0.494))
add_box('body', 'rear_spare_wheel_spoke_1', 3650, 142, 1008, 28, 205, 24, (0.851, 0.835, 0.784))
add_box('body', 'rear_spare_wheel_spoke_2', 3650, 71, 1130.98, 28, 205, 24, (0.851, 0.835, 0.784))
add_box('body', 'rear_spare_wheel_spoke_3', 3650, -71, 1130.98, 28, 205, 24, (0.851, 0.835, 0.784))
add_box('body', 'rear_spare_wheel_spoke_4', 3650, -142, 1008, 28, 205, 24, (0.851, 0.835, 0.784))
add_box('body', 'rear_spare_wheel_spoke_5', 3650, -71, 885.024, 28, 205, 24, (0.851, 0.835, 0.784))
add_box('body', 'rear_spare_wheel_spoke_6', 3650, 71, 885.024, 28, 205, 24, (0.851, 0.835, 0.784))
add_box('body', 'windshield_center_divider_bar', 1116, 0, 1570, 30, 42, 420, (0.067, 0.075, 0.082))
add_box('body', 'windshield_upper_inner_glare_band', 1112, 0, 1588, 20, 1210, 28, (0.149, 0.220, 0.247))
add_box('body', 'windshield_lower_inner_glare_band', 1112, 0, 1420, 20, 1185, 24, (0.149, 0.220, 0.247))
add_box('body', 'hood_front_lip_shadow', 42, 0, 1222, 36, 1320, 34, (0.616, 0.588, 0.494))
add_box('body', 'hood_rear_cowl_gap_shadow', 1012, 0, 1287, 28, 1310, 28, (0.114, 0.114, 0.114))
add_box('body', 'front_apron_lower_shadow', 92, 0, 710, 28, 1280, 42, (0.616, 0.588, 0.494))
add_box('front_detail', 'front_license_plate_upper_screw_left', -8, -155, 730, 18, 24, 24, (0.851, 0.835, 0.784))
add_box('front_detail', 'front_license_plate_upper_screw_right', -8, 155, 730, 18, 24, 24, (0.851, 0.835, 0.784))
add_box('front_detail', 'front_license_plate_lower_screw_left', -8, -155, 585, 18, 24, 24, (0.851, 0.835, 0.784))
add_box('front_detail', 'front_license_plate_lower_screw_right', -8, 155, 585, 18, 24, 24, (0.851, 0.835, 0.784))
add_cylinder('front_detail', 'front_bumper_face_bolt_1', 4, -680, 558, 'x', 34, 20, (0.851, 0.835, 0.784))
add_cylinder('front_detail', 'front_bumper_face_bolt_2', 4, -485, 558, 'x', 34, 20, (0.851, 0.835, 0.784))
add_cylinder('front_detail', 'front_bumper_face_bolt_3', 4, 485, 558, 'x', 34, 20, (0.851, 0.835, 0.784))
add_cylinder('front_detail', 'front_bumper_face_bolt_4', 4, 680, 558, 'x', 34, 20, (0.851, 0.835, 0.784))
add_cylinder('body', 'rear_bumper_face_bolt_1', 3742, -660, 558, 'x', 34, 20, (0.851, 0.835, 0.784))
add_cylinder('body', 'rear_bumper_face_bolt_2', 3742, -360, 558, 'x', 34, 20, (0.851, 0.835, 0.784))
add_cylinder('body', 'rear_bumper_face_bolt_3', 3742, 360, 558, 'x', 34, 20, (0.851, 0.835, 0.784))
add_cylinder('body', 'rear_bumper_face_bolt_4', 3742, 660, 558, 'x', 34, 20, (0.851, 0.835, 0.784))
add_cylinder('body', 'left_windshield_wiper_pivot', 1100, -358, 1372, 'x', 42, 26, (0.851, 0.835, 0.784))
add_box('body', 'left_windshield_wiper_blade_rubber', 1092, -165, 1508, 24, 480, 16, (0.114, 0.114, 0.114))
add_box('body', 'left_windshield_wiper_arm_chrome', 1094, -252, 1456, 18, 340, 14, (0.851, 0.835, 0.784))
add_cylinder('body', 'left_cowl_vent_screw_front', 1044, -278, 1360, 'z', 20, 12, (0.851, 0.835, 0.784))
add_cylinder('body', 'left_cowl_vent_screw_rear', 1018, -422, 1360, 'z', 20, 12, (0.851, 0.835, 0.784))
add_box('body', 'left_hood_side_gap_shadow', 420, -684, 1235, 760, 24, 24, (0.616, 0.588, 0.494))
add_cylinder('body', 'left_hood_latch_round_pin', 820, -645, 1238, 'y', 28, 22, (0.851, 0.835, 0.784))
add_cylinder('front_detail', 'left_front_fender_turn_signal_screw_front', 238, -642, 1078, 'z', 18, 12, (0.851, 0.835, 0.784))
add_cylinder('front_detail', 'left_front_fender_turn_signal_screw_rear', 350, -642, 1078, 'z', 18, 12, (0.851, 0.835, 0.784))
add_cylinder('front_detail', 'left_side_marker_chrome_bezel', 190, -682, 1005, 'y', 112, 18, (0.851, 0.835, 0.784))
add_cylinder('front_detail', 'left_fog_lamp_inner_glass', 16, -360, 620, 'x', 118, 18, (0.894, 0.863, 0.780))
add_box('front_detail', 'left_fog_lamp_drop_bracket', 42, -360, 548, 38, 34, 85, (0.176, 0.188, 0.200))
add_cylinder('body', 'left_mirror_mount_screw_1', 1328, -842, 1248, 'y', 20, 16, (0.851, 0.835, 0.784))
add_cylinder('body', 'left_mirror_mount_screw_2', 1328, -842, 1142, 'y', 20, 16, (0.851, 0.835, 0.784))
add_cylinder('body', 'left_mirror_mount_screw_3', 1484, -842, 1248, 'y', 20, 16, (0.851, 0.835, 0.784))
add_cylinder('body', 'left_mirror_mount_screw_4', 1484, -842, 1142, 'y', 20, 16, (0.851, 0.835, 0.784))
add_box('body', 'left_door_handle_shadow_gap', 1575, -834, 1016, 175, 18, 18, (0.616, 0.588, 0.494))
add_box('body', 'left_door_handle_chrome_face', 1575, -858, 1055, 140, 18, 22, (0.851, 0.835, 0.784))
add_box('body', 'left_front_door_lower_weather_strip', 1228, -836, 742, 760, 20, 22, (0.114, 0.114, 0.114))
add_box('body', 'left_rear_quarter_vertical_rear_seam', 2828, -832, 980, 24, 20, 560, (0.114, 0.114, 0.114))
add_cylinder('body', 'left_fuel_filler_outer_ring', 2935, -842, 1065, 'y', 145, 18, (0.851, 0.835, 0.784))
add_cylinder('hard_top', 'left_roof_gutter_rivet_1', 1240, -864, 1828, 'y', 18, 16, (0.851, 0.835, 0.784))
add_cylinder('hard_top', 'left_roof_gutter_rivet_2', 1485, -864, 1828, 'y', 18, 16, (0.851, 0.835, 0.784))
add_cylinder('hard_top', 'left_roof_gutter_rivet_3', 1730, -864, 1828, 'y', 18, 16, (0.851, 0.835, 0.784))
add_cylinder('hard_top', 'left_roof_gutter_rivet_4', 1975, -864, 1828, 'y', 18, 16, (0.851, 0.835, 0.784))
add_cylinder('hard_top', 'left_roof_gutter_rivet_5', 2220, -864, 1828, 'y', 18, 16, (0.851, 0.835, 0.784))
add_cylinder('hard_top', 'left_roof_gutter_rivet_6', 2465, -864, 1828, 'y', 18, 16, (0.851, 0.835, 0.784))
add_cylinder('hard_top', 'left_roof_gutter_rivet_7', 2710, -864, 1828, 'y', 18, 16, (0.851, 0.835, 0.784))
add_cylinder('hard_top', 'left_roof_gutter_rivet_8', 2955, -864, 1828, 'y', 18, 16, (0.851, 0.835, 0.784))
add_cylinder('hard_top', 'left_roof_gutter_rivet_9', 3200, -864, 1828, 'y', 18, 16, (0.851, 0.835, 0.784))
add_cylinder('hard_top', 'left_hardtop_front_window_upper_screw_1', 1240, -870, 1724, 'y', 18, 16, (0.851, 0.835, 0.784))
add_cylinder('hard_top', 'left_hardtop_front_window_lower_screw_1', 1240, -870, 1368, 'y', 18, 16, (0.851, 0.835, 0.784))
add_cylinder('hard_top', 'left_hardtop_front_window_upper_screw_2', 1600, -870, 1724, 'y', 18, 16, (0.851, 0.835, 0.784))
add_cylinder('hard_top', 'left_hardtop_front_window_lower_screw_2', 1600, -870, 1368, 'y', 18, 16, (0.851, 0.835, 0.784))
add_box('hard_top', 'left_hardtop_front_window_center_track', 1420, -868, 1435, 430, 14, 18, (0.851, 0.835, 0.784))
add_cylinder('hard_top', 'left_hardtop_rear_window_upper_screw_1', 1955, -870, 1724, 'y', 18, 16, (0.851, 0.835, 0.784))
add_cylinder('hard_top', 'left_hardtop_rear_window_lower_screw_1', 1955, -870, 1368, 'y', 18, 16, (0.851, 0.835, 0.784))
add_cylinder('hard_top', 'left_hardtop_rear_window_upper_screw_2', 2425, -870, 1724, 'y', 18, 16, (0.851, 0.835, 0.784))
add_cylinder('hard_top', 'left_hardtop_rear_window_lower_screw_2', 2425, -870, 1368, 'y', 18, 16, (0.851, 0.835, 0.784))
add_box('hard_top', 'left_hardtop_rear_window_center_track', 2190, -868, 1435, 540, 14, 18, (0.851, 0.835, 0.784))
add_box('hard_top', 'left_roof_gutter_front_end_cap', 1128, -862, 1812, 52, 34, 42, (0.851, 0.835, 0.784))
add_box('hard_top', 'left_roof_gutter_rear_end_cap', 3358, -862, 1812, 52, 34, 42, (0.851, 0.835, 0.784))
add_box('running_gear', 'front_left_rim_vent_slot_1', 877.894, -860, 477.5, 54, 20, 34, (0.149, 0.220, 0.247))
add_box('running_gear', 'front_left_rim_vent_slot_2', 735, -860, 560, 54, 20, 34, (0.149, 0.220, 0.247))
add_box('running_gear', 'front_left_rim_vent_slot_3', 592.106, -860, 477.5, 54, 20, 34, (0.149, 0.220, 0.247))
add_box('running_gear', 'front_left_rim_vent_slot_4', 592.106, -860, 312.5, 54, 20, 34, (0.149, 0.220, 0.247))
add_box('running_gear', 'front_left_rim_vent_slot_5', 735, -860, 230, 54, 20, 34, (0.149, 0.220, 0.247))
add_box('running_gear', 'front_left_rim_vent_slot_6', 877.894, -860, 312.5, 54, 20, 34, (0.149, 0.220, 0.247))
add_box('running_gear', 'front_left_tire_sidewall_tick_1', 1059.55, -865, 481.963, 38, 18, 18, (0.616, 0.588, 0.494))
add_box('running_gear', 'front_left_tire_sidewall_tick_2', 972.588, -865, 632.588, 38, 18, 18, (0.616, 0.588, 0.494))
add_box('running_gear', 'front_left_tire_sidewall_tick_3', 821.963, -865, 719.551, 38, 18, 18, (0.616, 0.588, 0.494))
add_box('running_gear', 'front_left_tire_sidewall_tick_4', 648.037, -865, 719.551, 38, 18, 18, (0.616, 0.588, 0.494))
add_box('running_gear', 'front_left_tire_sidewall_tick_5', 497.412, -865, 632.588, 38, 18, 18, (0.616, 0.588, 0.494))
add_box('running_gear', 'front_left_tire_sidewall_tick_6', 410.449, -865, 481.963, 38, 18, 18, (0.616, 0.588, 0.494))
add_box('running_gear', 'front_left_tire_sidewall_tick_7', 410.449, -865, 308.037, 38, 18, 18, (0.616, 0.588, 0.494))
add_box('running_gear', 'front_left_tire_sidewall_tick_8', 497.412, -865, 157.412, 38, 18, 18, (0.616, 0.588, 0.494))
add_box('running_gear', 'front_left_tire_sidewall_tick_9', 648.037, -865, 70.4489, 38, 18, 18, (0.616, 0.588, 0.494))
add_box('running_gear', 'front_left_tire_sidewall_tick_10', 821.963, -865, 70.4489, 38, 18, 18, (0.616, 0.588, 0.494))
add_box('running_gear', 'front_left_tire_sidewall_tick_11', 972.588, -865, 157.412, 38, 18, 18, (0.616, 0.588, 0.494))
add_box('running_gear', 'front_left_tire_sidewall_tick_12', 1059.55, -865, 308.037, 38, 18, 18, (0.616, 0.588, 0.494))
add_cylinder('running_gear', 'front_left_hub_cap_center_button', 735, -908, 395, 'y', 74, 24, (0.851, 0.835, 0.784))
add_box('running_gear', 'rear_left_rim_vent_slot_1', 3162.89, -860, 477.5, 54, 20, 34, (0.149, 0.220, 0.247))
add_box('running_gear', 'rear_left_rim_vent_slot_2', 3020, -860, 560, 54, 20, 34, (0.149, 0.220, 0.247))
add_box('running_gear', 'rear_left_rim_vent_slot_3', 2877.11, -860, 477.5, 54, 20, 34, (0.149, 0.220, 0.247))
add_box('running_gear', 'rear_left_rim_vent_slot_4', 2877.11, -860, 312.5, 54, 20, 34, (0.149, 0.220, 0.247))
add_box('running_gear', 'rear_left_rim_vent_slot_5', 3020, -860, 230, 54, 20, 34, (0.149, 0.220, 0.247))
add_box('running_gear', 'rear_left_rim_vent_slot_6', 3162.89, -860, 312.5, 54, 20, 34, (0.149, 0.220, 0.247))
add_box('running_gear', 'rear_left_tire_sidewall_tick_1', 3344.55, -865, 481.963, 38, 18, 18, (0.616, 0.588, 0.494))
add_box('running_gear', 'rear_left_tire_sidewall_tick_2', 3257.59, -865, 632.588, 38, 18, 18, (0.616, 0.588, 0.494))
add_box('running_gear', 'rear_left_tire_sidewall_tick_3', 3106.96, -865, 719.551, 38, 18, 18, (0.616, 0.588, 0.494))
add_box('running_gear', 'rear_left_tire_sidewall_tick_4', 2933.04, -865, 719.551, 38, 18, 18, (0.616, 0.588, 0.494))
add_box('running_gear', 'rear_left_tire_sidewall_tick_5', 2782.41, -865, 632.588, 38, 18, 18, (0.616, 0.588, 0.494))
add_box('running_gear', 'rear_left_tire_sidewall_tick_6', 2695.45, -865, 481.963, 38, 18, 18, (0.616, 0.588, 0.494))
add_box('running_gear', 'rear_left_tire_sidewall_tick_7', 2695.45, -865, 308.037, 38, 18, 18, (0.616, 0.588, 0.494))
add_box('running_gear', 'rear_left_tire_sidewall_tick_8', 2782.41, -865, 157.412, 38, 18, 18, (0.616, 0.588, 0.494))
add_box('running_gear', 'rear_left_tire_sidewall_tick_9', 2933.04, -865, 70.4489, 38, 18, 18, (0.616, 0.588, 0.494))
add_box('running_gear', 'rear_left_tire_sidewall_tick_10', 3106.96, -865, 70.4489, 38, 18, 18, (0.616, 0.588, 0.494))
add_box('running_gear', 'rear_left_tire_sidewall_tick_11', 3257.59, -865, 157.412, 38, 18, 18, (0.616, 0.588, 0.494))
add_box('running_gear', 'rear_left_tire_sidewall_tick_12', 3344.55, -865, 308.037, 38, 18, 18, (0.616, 0.588, 0.494))
add_cylinder('running_gear', 'rear_left_hub_cap_center_button', 3020, -908, 395, 'y', 74, 24, (0.851, 0.835, 0.784))
add_cylinder('body', 'right_windshield_wiper_pivot', 1100, 358, 1372, 'x', 42, 26, (0.851, 0.835, 0.784))
add_box('body', 'right_windshield_wiper_blade_rubber', 1092, 165, 1508, 24, 480, 16, (0.114, 0.114, 0.114))
add_box('body', 'right_windshield_wiper_arm_chrome', 1094, 252, 1456, 18, 340, 14, (0.851, 0.835, 0.784))
add_cylinder('body', 'right_cowl_vent_screw_front', 1044, 278, 1360, 'z', 20, 12, (0.851, 0.835, 0.784))
add_cylinder('body', 'right_cowl_vent_screw_rear', 1018, 422, 1360, 'z', 20, 12, (0.851, 0.835, 0.784))
add_box('body', 'right_hood_side_gap_shadow', 420, 684, 1235, 760, 24, 24, (0.616, 0.588, 0.494))
add_cylinder('body', 'right_hood_latch_round_pin', 820, 645, 1238, 'y', 28, 22, (0.851, 0.835, 0.784))
add_cylinder('front_detail', 'right_front_fender_turn_signal_screw_front', 238, 642, 1078, 'z', 18, 12, (0.851, 0.835, 0.784))
add_cylinder('front_detail', 'right_front_fender_turn_signal_screw_rear', 350, 642, 1078, 'z', 18, 12, (0.851, 0.835, 0.784))
add_cylinder('front_detail', 'right_side_marker_chrome_bezel', 190, 682, 1005, 'y', 112, 18, (0.851, 0.835, 0.784))
add_cylinder('front_detail', 'right_fog_lamp_inner_glass', 16, 360, 620, 'x', 118, 18, (0.894, 0.863, 0.780))
add_box('front_detail', 'right_fog_lamp_drop_bracket', 42, 360, 548, 38, 34, 85, (0.176, 0.188, 0.200))
add_cylinder('body', 'right_mirror_mount_screw_1', 1328, 842, 1248, 'y', 20, 16, (0.851, 0.835, 0.784))
add_cylinder('body', 'right_mirror_mount_screw_2', 1328, 842, 1142, 'y', 20, 16, (0.851, 0.835, 0.784))
add_cylinder('body', 'right_mirror_mount_screw_3', 1484, 842, 1248, 'y', 20, 16, (0.851, 0.835, 0.784))
add_cylinder('body', 'right_mirror_mount_screw_4', 1484, 842, 1142, 'y', 20, 16, (0.851, 0.835, 0.784))
add_box('body', 'right_door_handle_shadow_gap', 1575, 834, 1016, 175, 18, 18, (0.616, 0.588, 0.494))
add_box('body', 'right_door_handle_chrome_face', 1575, 858, 1055, 140, 18, 22, (0.851, 0.835, 0.784))
add_box('body', 'right_front_door_lower_weather_strip', 1228, 836, 742, 760, 20, 22, (0.114, 0.114, 0.114))
add_box('body', 'right_rear_quarter_vertical_rear_seam', 2828, 832, 980, 24, 20, 560, (0.114, 0.114, 0.114))
add_cylinder('body', 'right_fuel_filler_outer_ring', 2935, 842, 1065, 'y', 145, 18, (0.851, 0.835, 0.784))
add_cylinder('hard_top', 'right_roof_gutter_rivet_1', 1240, 864, 1828, 'y', 18, 16, (0.851, 0.835, 0.784))
add_cylinder('hard_top', 'right_roof_gutter_rivet_2', 1485, 864, 1828, 'y', 18, 16, (0.851, 0.835, 0.784))
add_cylinder('hard_top', 'right_roof_gutter_rivet_3', 1730, 864, 1828, 'y', 18, 16, (0.851, 0.835, 0.784))
add_cylinder('hard_top', 'right_roof_gutter_rivet_4', 1975, 864, 1828, 'y', 18, 16, (0.851, 0.835, 0.784))
add_cylinder('hard_top', 'right_roof_gutter_rivet_5', 2220, 864, 1828, 'y', 18, 16, (0.851, 0.835, 0.784))
add_cylinder('hard_top', 'right_roof_gutter_rivet_6', 2465, 864, 1828, 'y', 18, 16, (0.851, 0.835, 0.784))
add_cylinder('hard_top', 'right_roof_gutter_rivet_7', 2710, 864, 1828, 'y', 18, 16, (0.851, 0.835, 0.784))
add_cylinder('hard_top', 'right_roof_gutter_rivet_8', 2955, 864, 1828, 'y', 18, 16, (0.851, 0.835, 0.784))
add_cylinder('hard_top', 'right_roof_gutter_rivet_9', 3200, 864, 1828, 'y', 18, 16, (0.851, 0.835, 0.784))
add_cylinder('hard_top', 'right_hardtop_front_window_upper_screw_1', 1240, 870, 1724, 'y', 18, 16, (0.851, 0.835, 0.784))
add_cylinder('hard_top', 'right_hardtop_front_window_lower_screw_1', 1240, 870, 1368, 'y', 18, 16, (0.851, 0.835, 0.784))
add_cylinder('hard_top', 'right_hardtop_front_window_upper_screw_2', 1600, 870, 1724, 'y', 18, 16, (0.851, 0.835, 0.784))
add_cylinder('hard_top', 'right_hardtop_front_window_lower_screw_2', 1600, 870, 1368, 'y', 18, 16, (0.851, 0.835, 0.784))
add_box('hard_top', 'right_hardtop_front_window_center_track', 1420, 868, 1435, 430, 14, 18, (0.851, 0.835, 0.784))
add_cylinder('hard_top', 'right_hardtop_rear_window_upper_screw_1', 1955, 870, 1724, 'y', 18, 16, (0.851, 0.835, 0.784))
add_cylinder('hard_top', 'right_hardtop_rear_window_lower_screw_1', 1955, 870, 1368, 'y', 18, 16, (0.851, 0.835, 0.784))
add_cylinder('hard_top', 'right_hardtop_rear_window_upper_screw_2', 2425, 870, 1724, 'y', 18, 16, (0.851, 0.835, 0.784))
add_cylinder('hard_top', 'right_hardtop_rear_window_lower_screw_2', 2425, 870, 1368, 'y', 18, 16, (0.851, 0.835, 0.784))
add_box('hard_top', 'right_hardtop_rear_window_center_track', 2190, 868, 1435, 540, 14, 18, (0.851, 0.835, 0.784))
add_box('hard_top', 'right_roof_gutter_front_end_cap', 1128, 862, 1812, 52, 34, 42, (0.851, 0.835, 0.784))
add_box('hard_top', 'right_roof_gutter_rear_end_cap', 3358, 862, 1812, 52, 34, 42, (0.851, 0.835, 0.784))
add_box('running_gear', 'front_right_rim_vent_slot_1', 877.894, 860, 477.5, 54, 20, 34, (0.149, 0.220, 0.247))
add_box('running_gear', 'front_right_rim_vent_slot_2', 735, 860, 560, 54, 20, 34, (0.149, 0.220, 0.247))
add_box('running_gear', 'front_right_rim_vent_slot_3', 592.106, 860, 477.5, 54, 20, 34, (0.149, 0.220, 0.247))
add_box('running_gear', 'front_right_rim_vent_slot_4', 592.106, 860, 312.5, 54, 20, 34, (0.149, 0.220, 0.247))
add_box('running_gear', 'front_right_rim_vent_slot_5', 735, 860, 230, 54, 20, 34, (0.149, 0.220, 0.247))
add_box('running_gear', 'front_right_rim_vent_slot_6', 877.894, 860, 312.5, 54, 20, 34, (0.149, 0.220, 0.247))
add_box('running_gear', 'front_right_tire_sidewall_tick_1', 1059.55, 865, 481.963, 38, 18, 18, (0.616, 0.588, 0.494))
add_box('running_gear', 'front_right_tire_sidewall_tick_2', 972.588, 865, 632.588, 38, 18, 18, (0.616, 0.588, 0.494))
add_box('running_gear', 'front_right_tire_sidewall_tick_3', 821.963, 865, 719.551, 38, 18, 18, (0.616, 0.588, 0.494))
add_box('running_gear', 'front_right_tire_sidewall_tick_4', 648.037, 865, 719.551, 38, 18, 18, (0.616, 0.588, 0.494))
add_box('running_gear', 'front_right_tire_sidewall_tick_5', 497.412, 865, 632.588, 38, 18, 18, (0.616, 0.588, 0.494))
add_box('running_gear', 'front_right_tire_sidewall_tick_6', 410.449, 865, 481.963, 38, 18, 18, (0.616, 0.588, 0.494))
add_box('running_gear', 'front_right_tire_sidewall_tick_7', 410.449, 865, 308.037, 38, 18, 18, (0.616, 0.588, 0.494))
add_box('running_gear', 'front_right_tire_sidewall_tick_8', 497.412, 865, 157.412, 38, 18, 18, (0.616, 0.588, 0.494))
add_box('running_gear', 'front_right_tire_sidewall_tick_9', 648.037, 865, 70.4489, 38, 18, 18, (0.616, 0.588, 0.494))
add_box('running_gear', 'front_right_tire_sidewall_tick_10', 821.963, 865, 70.4489, 38, 18, 18, (0.616, 0.588, 0.494))
add_box('running_gear', 'front_right_tire_sidewall_tick_11', 972.588, 865, 157.412, 38, 18, 18, (0.616, 0.588, 0.494))
add_box('running_gear', 'front_right_tire_sidewall_tick_12', 1059.55, 865, 308.037, 38, 18, 18, (0.616, 0.588, 0.494))
add_cylinder('running_gear', 'front_right_hub_cap_center_button', 735, 908, 395, 'y', 74, 24, (0.851, 0.835, 0.784))
add_box('running_gear', 'rear_right_rim_vent_slot_1', 3162.89, 860, 477.5, 54, 20, 34, (0.149, 0.220, 0.247))
add_box('running_gear', 'rear_right_rim_vent_slot_2', 3020, 860, 560, 54, 20, 34, (0.149, 0.220, 0.247))
add_box('running_gear', 'rear_right_rim_vent_slot_3', 2877.11, 860, 477.5, 54, 20, 34, (0.149, 0.220, 0.247))
add_box('running_gear', 'rear_right_rim_vent_slot_4', 2877.11, 860, 312.5, 54, 20, 34, (0.149, 0.220, 0.247))
add_box('running_gear', 'rear_right_rim_vent_slot_5', 3020, 860, 230, 54, 20, 34, (0.149, 0.220, 0.247))
add_box('running_gear', 'rear_right_rim_vent_slot_6', 3162.89, 860, 312.5, 54, 20, 34, (0.149, 0.220, 0.247))
add_box('running_gear', 'rear_right_tire_sidewall_tick_1', 3344.55, 865, 481.963, 38, 18, 18, (0.616, 0.588, 0.494))
add_box('running_gear', 'rear_right_tire_sidewall_tick_2', 3257.59, 865, 632.588, 38, 18, 18, (0.616, 0.588, 0.494))
add_box('running_gear', 'rear_right_tire_sidewall_tick_3', 3106.96, 865, 719.551, 38, 18, 18, (0.616, 0.588, 0.494))
add_box('running_gear', 'rear_right_tire_sidewall_tick_4', 2933.04, 865, 719.551, 38, 18, 18, (0.616, 0.588, 0.494))
add_box('running_gear', 'rear_right_tire_sidewall_tick_5', 2782.41, 865, 632.588, 38, 18, 18, (0.616, 0.588, 0.494))
add_box('running_gear', 'rear_right_tire_sidewall_tick_6', 2695.45, 865, 481.963, 38, 18, 18, (0.616, 0.588, 0.494))
add_box('running_gear', 'rear_right_tire_sidewall_tick_7', 2695.45, 865, 308.037, 38, 18, 18, (0.616, 0.588, 0.494))
add_box('running_gear', 'rear_right_tire_sidewall_tick_8', 2782.41, 865, 157.412, 38, 18, 18, (0.616, 0.588, 0.494))
add_box('running_gear', 'rear_right_tire_sidewall_tick_9', 2933.04, 865, 70.4489, 38, 18, 18, (0.616, 0.588, 0.494))
add_box('running_gear', 'rear_right_tire_sidewall_tick_10', 3106.96, 865, 70.4489, 38, 18, 18, (0.616, 0.588, 0.494))
add_box('running_gear', 'rear_right_tire_sidewall_tick_11', 3257.59, 865, 157.412, 38, 18, 18, (0.616, 0.588, 0.494))
add_box('running_gear', 'rear_right_tire_sidewall_tick_12', 3344.55, 865, 308.037, 38, 18, 18, (0.616, 0.588, 0.494))
add_cylinder('running_gear', 'rear_right_hub_cap_center_button', 3020, 908, 395, 'y', 74, 24, (0.851, 0.835, 0.784))
add_box('hard_top', 'rear_left_window_upper_inner_shadow', 3492, -250, 1688, 20, 260, 22, (0.149, 0.220, 0.247))
add_box('hard_top', 'rear_right_window_upper_inner_shadow', 3492, 250, 1688, 20, 260, 22, (0.149, 0.220, 0.247))
add_box('hard_top', 'rear_left_window_lower_inner_shadow', 3492, -250, 1496, 20, 275, 20, (0.149, 0.220, 0.247))
add_box('hard_top', 'rear_right_window_lower_inner_shadow', 3492, 250, 1496, 20, 275, 20, (0.149, 0.220, 0.247))
add_box('hard_top', 'rear_left_window_pale_glare_strip', 3508, -250, 1698, 16, 230, 14, (0.894, 0.863, 0.780))
add_box('hard_top', 'rear_right_window_pale_glare_strip', 3508, 250, 1698, 16, 230, 14, (0.894, 0.863, 0.780))
add_box('hard_top', 'rear_door_hinge_mount_plate_1', 3528, -620, 1510, 24, 84, 96, (0.851, 0.835, 0.784))
add_box('hard_top', 'rear_door_hinge_mount_plate_2', 3528, -520, 1180, 24, 84, 96, (0.851, 0.835, 0.784))
add_box('hard_top', 'rear_door_hinge_mount_plate_3', 3528, 520, 1180, 24, 84, 96, (0.851, 0.835, 0.784))
add_box('hard_top', 'rear_door_hinge_mount_plate_4', 3528, 620, 1510, 24, 84, 96, (0.851, 0.835, 0.784))
add_cylinder('hard_top', 'rear_door_hinge_plate_screw_1', 3544, -590, 1555, 'x', 18, 16, (0.851, 0.835, 0.784))
add_cylinder('hard_top', 'rear_door_hinge_plate_screw_2', 3544, -590, 1470, 'x', 18, 16, (0.851, 0.835, 0.784))
add_cylinder('hard_top', 'rear_door_hinge_plate_screw_3', 3544, 590, 1555, 'x', 18, 16, (0.851, 0.835, 0.784))
add_cylinder('hard_top', 'rear_door_hinge_plate_screw_4', 3544, 590, 1470, 'x', 18, 16, (0.851, 0.835, 0.784))
add_cylinder('hard_top', 'rear_door_hinge_plate_screw_5', 3544, -590, 1225, 'x', 18, 16, (0.851, 0.835, 0.784))
add_cylinder('hard_top', 'rear_door_hinge_plate_screw_6', 3544, -590, 1138, 'x', 18, 16, (0.851, 0.835, 0.784))
add_cylinder('hard_top', 'rear_door_hinge_plate_screw_7', 3544, 590, 1225, 'x', 18, 16, (0.851, 0.835, 0.784))
add_cylinder('hard_top', 'rear_door_hinge_plate_screw_8', 3544, 590, 1138, 'x', 18, 16, (0.851, 0.835, 0.784))
add_box('body', 'rear_spare_carrier_latch_plate', 3530, 315, 1042, 36, 132, 92, (0.722, 0.722, 0.722))
add_cylinder('body', 'rear_spare_carrier_latch_pin', 3552, 315, 1042, 'x', 28, 36, (0.851, 0.835, 0.784))
add_box('body', 'rear_spare_carrier_lower_hinge_plate', 3528, -320, 760, 36, 126, 88, (0.722, 0.722, 0.722))
add_box('body', 'rear_spare_carrier_upper_hinge_plate', 3528, -320, 1088, 36, 126, 88, (0.722, 0.722, 0.722))
add_cylinder('body', 'rear_spare_carrier_hardware_screw_1', 3550, -320, 724, 'x', 18, 16, (0.851, 0.835, 0.784))
add_cylinder('body', 'rear_spare_carrier_hardware_screw_2', 3550, -320, 796, 'x', 18, 16, (0.851, 0.835, 0.784))
add_cylinder('body', 'rear_spare_carrier_hardware_screw_3', 3550, -320, 1052, 'x', 18, 16, (0.851, 0.835, 0.784))
add_cylinder('body', 'rear_spare_carrier_hardware_screw_4', 3550, -320, 1124, 'x', 18, 16, (0.851, 0.835, 0.784))
add_cylinder('body', 'rear_spare_carrier_hardware_screw_5', 3550, 315, 1006, 'x', 18, 16, (0.851, 0.835, 0.784))
add_cylinder('body', 'rear_spare_carrier_hardware_screw_6', 3550, 315, 1078, 'x', 18, 16, (0.851, 0.835, 0.784))
add_box('body', 'rear_license_plate_upper_lamp_left', 3508, -145, 810, 28, 90, 34, (0.851, 0.835, 0.784))
add_box('body', 'rear_license_plate_upper_lamp_right', 3508, 145, 810, 28, 90, 34, (0.851, 0.835, 0.784))
add_cylinder('body', 'rear_license_plate_screw_1', 3534, -160, 770, 'x', 18, 16, (0.851, 0.835, 0.784))
add_cylinder('body', 'rear_license_plate_screw_2', 3534, 160, 770, 'x', 18, 16, (0.851, 0.835, 0.784))
add_cylinder('body', 'rear_license_plate_screw_3', 3534, -160, 630, 'x', 18, 16, (0.851, 0.835, 0.784))
add_cylinder('body', 'rear_license_plate_screw_4', 3534, 160, 630, 'x', 18, 16, (0.851, 0.835, 0.784))
add_cylinder('body', 'rear_left_tail_lamp_chrome_bezel', 3488, -675, 930, 'x', 122, 18, (0.851, 0.835, 0.784))
add_cylinder('body', 'rear_left_tail_lamp_inner_lens', 3502, -675, 930, 'x', 72, 18, (0.839, 0.278, 0.216))
add_cylinder('body', 'rear_right_tail_lamp_chrome_bezel', 3488, 675, 930, 'x', 122, 18, (0.851, 0.835, 0.784))
add_cylinder('body', 'rear_right_tail_lamp_inner_lens', 3502, 675, 930, 'x', 72, 18, (0.839, 0.278, 0.216))
add_box('hard_top', 'roof_ventilator_lid_panel', 1885, 0, 1882, 520, 520, 30, (0.945, 0.933, 0.894))
add_box('hard_top', 'roof_ventilator_front_hinge_bar', 1625, 0, 1898, 36, 540, 34, (0.851, 0.835, 0.784))
add_box('hard_top', 'roof_ventilator_rear_pull_handle', 2140, 0, 1905, 46, 210, 34, (0.851, 0.835, 0.784))
add_box('hard_top', 'roof_ventilator_shadow_gap', 1885, 0, 1858, 560, 560, 24, (0.616, 0.588, 0.494))
add_cylinder('hard_top', 'roof_ventilator_screw_1', 1642, -220, 1918, 'z', 18, 14, (0.851, 0.835, 0.784))
add_cylinder('hard_top', 'roof_ventilator_screw_2', 1642, 220, 1918, 'z', 18, 14, (0.851, 0.835, 0.784))
add_cylinder('hard_top', 'roof_ventilator_screw_3', 2115, -185, 1918, 'z', 18, 14, (0.851, 0.835, 0.784))
add_cylinder('hard_top', 'roof_ventilator_screw_4', 2115, 185, 1918, 'z', 18, 14, (0.851, 0.835, 0.784))
add_box('hard_top', 'left_rear_quarter_ventilator_frame', 3065, -846, 1548, 270, 24, 255, (0.067, 0.075, 0.082))
add_box('hard_top', 'left_rear_quarter_ventilator_louver_1', 3065, -872, 1488, 225, 18, 18, (0.149, 0.220, 0.247))
add_box('hard_top', 'left_rear_quarter_ventilator_louver_2', 3065, -872, 1534, 225, 18, 18, (0.149, 0.220, 0.247))
add_box('hard_top', 'left_rear_quarter_ventilator_louver_3', 3065, -872, 1580, 225, 18, 18, (0.149, 0.220, 0.247))
add_box('hard_top', 'left_rear_quarter_ventilator_louver_4', 3065, -872, 1626, 225, 18, 18, (0.149, 0.220, 0.247))
add_box('hard_top', 'left_hardtop_to_tub_join_shadow', 2200, -822, 1262, 2190, 24, 34, (0.114, 0.114, 0.114))
add_box('body', 'left_front_clip_to_tub_join_line', 1018, -823, 958, 22, 22, 510, (0.114, 0.114, 0.114))
add_box('body', 'left_rear_tub_top_flange', 2325, -805, 1235, 1360, 42, 36, (0.894, 0.863, 0.780))
add_box('hard_top', 'right_rear_quarter_ventilator_frame', 3065, 846, 1548, 270, 24, 255, (0.067, 0.075, 0.082))
add_box('hard_top', 'right_rear_quarter_ventilator_louver_1', 3065, 872, 1488, 225, 18, 18, (0.149, 0.220, 0.247))
add_box('hard_top', 'right_rear_quarter_ventilator_louver_2', 3065, 872, 1534, 225, 18, 18, (0.149, 0.220, 0.247))
add_box('hard_top', 'right_rear_quarter_ventilator_louver_3', 3065, 872, 1580, 225, 18, 18, (0.149, 0.220, 0.247))
add_box('hard_top', 'right_rear_quarter_ventilator_louver_4', 3065, 872, 1626, 225, 18, 18, (0.149, 0.220, 0.247))
add_box('hard_top', 'right_hardtop_to_tub_join_shadow', 2200, 822, 1262, 2190, 24, 34, (0.114, 0.114, 0.114))
add_box('body', 'right_front_clip_to_tub_join_line', 1018, 823, 958, 22, 22, 510, (0.114, 0.114, 0.114))
add_box('body', 'right_rear_tub_top_flange', 2325, 805, 1235, 1360, 42, 36, (0.894, 0.863, 0.780))
add_cylinder('chassis', 'cab_body_mount_rubber_puck_1', 710, -525, 560, 'z', 112, 42, (0.114, 0.114, 0.114))
add_box('chassis', 'cab_body_mount_stand_1', 710, -525, 500, 135, 120, 52, (0.176, 0.188, 0.200))
add_cylinder('chassis', 'cab_body_mount_rubber_puck_2', 710, 525, 560, 'z', 112, 42, (0.114, 0.114, 0.114))
add_box('chassis', 'cab_body_mount_stand_2', 710, 525, 500, 135, 120, 52, (0.176, 0.188, 0.200))
add_cylinder('chassis', 'cab_body_mount_rubber_puck_3', 1310, -560, 560, 'z', 112, 42, (0.114, 0.114, 0.114))
add_box('chassis', 'cab_body_mount_stand_3', 1310, -560, 500, 135, 120, 52, (0.176, 0.188, 0.200))
add_cylinder('chassis', 'cab_body_mount_rubber_puck_4', 1310, 560, 560, 'z', 112, 42, (0.114, 0.114, 0.114))
add_box('chassis', 'cab_body_mount_stand_4', 1310, 560, 500, 135, 120, 52, (0.176, 0.188, 0.200))
add_cylinder('chassis', 'cab_body_mount_rubber_puck_5', 2230, -575, 560, 'z', 112, 42, (0.114, 0.114, 0.114))
add_box('chassis', 'cab_body_mount_stand_5', 2230, -575, 500, 135, 120, 52, (0.176, 0.188, 0.200))
add_cylinder('chassis', 'cab_body_mount_rubber_puck_6', 2230, 575, 560, 'z', 112, 42, (0.114, 0.114, 0.114))
add_box('chassis', 'cab_body_mount_stand_6', 2230, 575, 500, 135, 120, 52, (0.176, 0.188, 0.200))
add_cylinder('chassis', 'cab_body_mount_rubber_puck_7', 3060, -545, 560, 'z', 112, 42, (0.114, 0.114, 0.114))
add_box('chassis', 'cab_body_mount_stand_7', 3060, -545, 500, 135, 120, 52, (0.176, 0.188, 0.200))
add_cylinder('chassis', 'cab_body_mount_rubber_puck_8', 3060, 545, 560, 'z', 112, 42, (0.114, 0.114, 0.114))
add_box('chassis', 'cab_body_mount_stand_8', 3060, 545, 500, 135, 120, 52, (0.176, 0.188, 0.200))
add_box('chassis', 'left_front_bumper_stay_outer_plate', 190, -585, 505, 310, 44, 88, (0.176, 0.188, 0.200))
add_box('chassis', 'left_front_bumper_stay_inner_plate', 188, -430, 487, 285, 38, 72, (0.176, 0.188, 0.200))
add_box('chassis', 'left_rear_bumper_stay_outer_plate', 3475, -585, 505, 320, 44, 88, (0.176, 0.188, 0.200))
add_box('chassis', 'left_rear_bumper_stay_inner_plate', 3482, -430, 488, 290, 38, 72, (0.176, 0.188, 0.200))
add_cylinder('chassis', 'left_front_bumper_stay_bolt_1', 105, -620, 550, 'y', 28, 22, (0.851, 0.835, 0.784))
add_cylinder('chassis', 'left_front_bumper_stay_bolt_2', 250, -620, 550, 'y', 28, 22, (0.851, 0.835, 0.784))
add_cylinder('chassis', 'left_rear_bumper_stay_bolt_1', 3415, -620, 550, 'y', 28, 22, (0.851, 0.835, 0.784))
add_cylinder('chassis', 'left_rear_bumper_stay_bolt_2', 3570, -620, 550, 'y', 28, 22, (0.851, 0.835, 0.784))
add_box('chassis', 'right_front_bumper_stay_outer_plate', 190, 585, 505, 310, 44, 88, (0.176, 0.188, 0.200))
add_box('chassis', 'right_front_bumper_stay_inner_plate', 188, 430, 487, 285, 38, 72, (0.176, 0.188, 0.200))
add_box('chassis', 'right_rear_bumper_stay_outer_plate', 3475, 585, 505, 320, 44, 88, (0.176, 0.188, 0.200))
add_box('chassis', 'right_rear_bumper_stay_inner_plate', 3482, 430, 488, 290, 38, 72, (0.176, 0.188, 0.200))
add_cylinder('chassis', 'right_front_bumper_stay_bolt_1', 105, 620, 550, 'y', 28, 22, (0.851, 0.835, 0.784))
add_cylinder('chassis', 'right_front_bumper_stay_bolt_2', 250, 620, 550, 'y', 28, 22, (0.851, 0.835, 0.784))
add_cylinder('chassis', 'right_rear_bumper_stay_bolt_1', 3415, 620, 550, 'y', 28, 22, (0.851, 0.835, 0.784))
add_cylinder('chassis', 'right_rear_bumper_stay_bolt_2', 3570, 620, 550, 'y', 28, 22, (0.851, 0.835, 0.784))
add_box('body', 'hood_underside_front_crossbrace', 285, 0, 1194, 760, 52, 34, (0.616, 0.588, 0.494))
add_box('body', 'hood_underside_rear_crossbrace', 930, 0, 1260, 520, 48, 32, (0.616, 0.588, 0.494))
add_box('body', 'left_hood_underside_diagonal_brace', 575, -330, 1224, 650, 36, 30, (0.616, 0.588, 0.494))
add_box('body', 'left_hood_hinge_mount_plate', 1015, -540, 1278, 116, 76, 24, (0.851, 0.835, 0.784))
add_cylinder('body', 'left_hood_hinge_mount_screw_front', 986, -540, 1298, 'z', 18, 12, (0.851, 0.835, 0.784))
add_cylinder('body', 'left_hood_hinge_mount_screw_rear', 1044, -540, 1298, 'z', 18, 12, (0.851, 0.835, 0.784))
add_box('body', 'right_hood_underside_diagonal_brace', 575, 330, 1224, 650, 36, 30, (0.616, 0.588, 0.494))
add_box('body', 'right_hood_hinge_mount_plate', 1015, 540, 1278, 116, 76, 24, (0.851, 0.835, 0.784))
add_cylinder('body', 'right_hood_hinge_mount_screw_front', 986, 540, 1298, 'z', 18, 12, (0.851, 0.835, 0.784))
add_cylinder('body', 'right_hood_hinge_mount_screw_rear', 1044, 540, 1298, 'z', 18, 12, (0.851, 0.835, 0.784))
add_cylinder('body', 'hood_prop_rod_stowed', 650, -585, 1170, 'x', 18, 690, (0.851, 0.835, 0.784))
add_box('body', 'hood_prop_rod_retaining_clip', 972, -585, 1182, 42, 34, 28, (0.851, 0.835, 0.784))
add_box('body', 'hood_lock_receiver_plate', 118, 0, 1166, 58, 250, 46, (0.851, 0.835, 0.784))
add_box('brake_system', 'proportioning_bypass_valve_body', 1505, 338, 608, 135, 82, 58, (0.769, 0.604, 0.239))
add_cylinder('brake_system', 'proportioning_valve_front_tube', 1398, 338, 610, 'x', 14, 210, (0.769, 0.604, 0.239))
add_cylinder('brake_system', 'proportioning_valve_rear_tube', 1610, 338, 610, 'x', 14, 220, (0.769, 0.604, 0.239))
add_box('brake_system', 'rear_brake_tube_frame_clip_1', 1835, 338, 590, 36, 32, 30, (0.851, 0.835, 0.784))
add_box('brake_system', 'rear_brake_tube_frame_clip_2', 2140, 338, 590, 36, 32, 30, (0.851, 0.835, 0.784))
add_box('brake_system', 'rear_brake_tube_frame_clip_3', 2445, 338, 590, 36, 32, 30, (0.851, 0.835, 0.784))
add_box('brake_system', 'rear_brake_tube_frame_clip_4', 2750, 338, 590, 36, 32, 30, (0.851, 0.835, 0.784))
add_cylinder('fuel_system', 'fuel_tank_sub_inlet_hose', 3020, -612, 745, 'z', 46, 320, (0.114, 0.114, 0.114))
add_cylinder('fuel_system', 'fuel_tank_sub_inlet_hose_clamp_1', 3020, -612, 622, 'z', 58, 14, (0.851, 0.835, 0.784))
add_cylinder('fuel_system', 'fuel_tank_sub_inlet_hose_clamp_2', 3020, -612, 850, 'z', 58, 14, (0.851, 0.835, 0.784))
add_cylinder('fuel_system', 'fuel_tank_vent_hose', 2870, -515, 720, 'x', 26, 470, (0.114, 0.114, 0.114))
add_box('body', 'rear_left_tail_lamp_amber_upper_lens', 3512, -675, 982, 24, 88, 42, (0.851, 0.471, 0.141))
add_box('body', 'rear_left_tail_lamp_red_center_lens', 3512, -675, 930, 24, 88, 42, (0.839, 0.278, 0.216))
add_box('body', 'rear_left_tail_lamp_clear_lower_lens', 3512, -675, 878, 24, 88, 42, (0.910, 0.910, 0.910))
add_cylinder('body', 'rear_left_tail_lamp_body_screw_1', 3530, -724, 1016, 'x', 16, 14, (0.851, 0.835, 0.784))
add_cylinder('body', 'rear_left_tail_lamp_body_screw_2', 3530, -724, 842, 'x', 16, 14, (0.851, 0.835, 0.784))
add_box('body', 'rear_right_tail_lamp_amber_upper_lens', 3512, 675, 982, 24, 88, 42, (0.851, 0.471, 0.141))
add_box('body', 'rear_right_tail_lamp_red_center_lens', 3512, 675, 930, 24, 88, 42, (0.839, 0.278, 0.216))
add_box('body', 'rear_right_tail_lamp_clear_lower_lens', 3512, 675, 878, 24, 88, 42, (0.910, 0.910, 0.910))
add_cylinder('body', 'rear_right_tail_lamp_body_screw_1', 3530, 724, 1016, 'x', 16, 14, (0.851, 0.835, 0.784))
add_cylinder('body', 'rear_right_tail_lamp_body_screw_2', 3530, 724, 842, 'x', 16, 14, (0.851, 0.835, 0.784))
add_cylinder('interior', 'dash_speedometer_chrome_bezel', 1190, 420, 1148, 'x', 128, 18, (0.851, 0.835, 0.784))
add_cylinder('interior', 'dash_speedometer_dark_face', 1180, 420, 1148, 'x', 108, 12, (0.149, 0.220, 0.247))
add_cylinder('interior', 'dash_fuel_chrome_bezel', 1190, 528, 1148, 'x', 72, 18, (0.851, 0.835, 0.784))
add_cylinder('interior', 'dash_fuel_dark_face', 1180, 528, 1148, 'x', 52, 12, (0.149, 0.220, 0.247))
add_cylinder('interior', 'dash_temperature_chrome_bezel', 1190, 312, 1148, 'x', 72, 18, (0.851, 0.835, 0.784))
add_cylinder('interior', 'dash_temperature_dark_face', 1180, 312, 1148, 'x', 52, 12, (0.149, 0.220, 0.247))
add_cylinder('interior', 'dash_oil_pressure_chrome_bezel', 1190, 220, 1148, 'x', 58, 18, (0.851, 0.835, 0.784))
add_cylinder('interior', 'dash_oil_pressure_dark_face', 1180, 220, 1148, 'x', 38, 12, (0.149, 0.220, 0.247))
add_cylinder('interior', 'dash_ammeter_chrome_bezel', 1190, 620, 1148, 'x', 58, 18, (0.851, 0.835, 0.784))
add_cylinder('interior', 'dash_ammeter_dark_face', 1180, 620, 1148, 'x', 38, 12, (0.149, 0.220, 0.247))
add_box('interior', 'dash_passenger_grab_handle_left_mount', 1190, -592, 1170, 38, 36, 74, (0.851, 0.835, 0.784))
add_box('interior', 'dash_passenger_grab_handle_right_mount', 1190, -245, 1170, 38, 36, 74, (0.851, 0.835, 0.784))
add_cylinder('interior', 'dash_passenger_grab_handle_bar', 1184, -420, 1198, 'y', 32, 330, (0.851, 0.835, 0.784))
add_box('interior', 'dashboard_glovebox_door', 1212, -420, 1115, 35, 335, 150, (0.910, 0.910, 0.910))
add_box('interior', 'dash_instrument_cluster_plate', 1208, 420, 1128, 36, 330, 170, (0.910, 0.910, 0.910))
add_cylinder('interior', 'dash_switch_knob_1', 1200, 535, 1050, 'x', 34, 26, (0.722, 0.722, 0.722))
add_cylinder('interior', 'dash_switch_knob_2', 1200, 480, 1050, 'x', 34, 26, (0.722, 0.722, 0.722))
add_cylinder('interior', 'dash_switch_knob_3', 1200, 425, 1050, 'x', 34, 26, (0.722, 0.722, 0.722))
add_cylinder('interior', 'dash_switch_knob_4', 1200, 370, 1050, 'x', 34, 26, (0.722, 0.722, 0.722))
add_cylinder('interior', 'dash_switch_knob_5', 1200, 315, 1050, 'x', 34, 26, (0.722, 0.722, 0.722))
add_cylinder('interior', 'heater_control_knob_1', 1200, -90, 1048, 'x', 30, 24, (0.722, 0.722, 0.722))
add_cylinder('interior', 'heater_control_knob_2', 1200, -155, 1048, 'x', 30, 24, (0.722, 0.722, 0.722))
add_cylinder('interior', 'heater_control_knob_3', 1200, -220, 1048, 'x', 30, 24, (0.722, 0.722, 0.722))
add_cylinder('interior', 'heater_control_knob_4', 1200, -285, 1048, 'x', 30, 24, (0.722, 0.722, 0.722))
add_box('interior', 'steering_wheel_spoke_1', 1216, 330, 1205, 34, 170, 18, (0.722, 0.722, 0.722))
add_box('interior', 'steering_wheel_spoke_2', 1216, 420, 1205, 34, 170, 18, (0.722, 0.722, 0.722))
add_box('interior', 'steering_wheel_spoke_3', 1216, 510, 1205, 34, 170, 18, (0.722, 0.722, 0.722))
add_box('interior', 'clutch_pedal_pad', 1340, 350, 705, 90, 45, 110, (0.114, 0.114, 0.114))
add_cylinder('interior', 'clutch_pedal_arm', 1300, 350, 820, 'z', 22, 240, (0.722, 0.722, 0.722))
add_box('interior', 'brake_pedal_pad', 1340, 440, 705, 90, 45, 110, (0.114, 0.114, 0.114))
add_cylinder('interior', 'brake_pedal_arm', 1300, 440, 820, 'z', 22, 240, (0.722, 0.722, 0.722))
add_box('interior', 'accelerator_pedal_pad', 1340, 520, 705, 90, 45, 110, (0.114, 0.114, 0.114))
add_cylinder('interior', 'accelerator_pedal_arm', 1300, 520, 820, 'z', 22, 240, (0.722, 0.722, 0.722))
add_box('interior', 'rhd_pedal_box_reinforcement', 1195, 465, 850, 95, 285, 250, (0.722, 0.722, 0.722))
add_box('interior', 'rhd_steering_column_dash_bracket', 1215, 420, 1040, 62, 210, 66, (0.722, 0.722, 0.722))
add_cylinder('interior', 'steering_column_firewall_boot', 1142, 420, 1020, 'x', 130, 48, (0.114, 0.114, 0.114))
add_cylinder('interior', 'brake_pedal_pivot_bar', 1260, 440, 960, 'y', 32, 180, (0.722, 0.722, 0.722))
add_cylinder('interior', 'clutch_pedal_pivot_bar', 1260, 350, 960, 'y', 32, 170, (0.722, 0.722, 0.722))
add_box('interior', 'accelerator_linkage_pivot', 1225, 538, 875, 52, 42, 125, (0.722, 0.722, 0.722))
add_cylinder('interior', 'steering_column_indicator_stalk', 1225, 605, 1220, 'y', 22, 165, (0.722, 0.722, 0.722))
add_box('interior', 'driver_side_floor_dimmer_switch', 1290, 650, 735, 70, 55, 34, (0.114, 0.114, 0.114))
add_cylinder('interior', 'handbrake_lever', 1760, 250, 790, 'z', 32, 360, (0.722, 0.722, 0.722))
add_cylinder('interior', 'gearshift_knob', 1500, -35, 1160, 'z', 86, 60, (0.114, 0.114, 0.114))
add_cylinder('interior', 'transfer_case_knob', 1580, -120, 1110, 'z', 76, 55, (0.114, 0.114, 0.114))
add_box('interior', 'front_left_seat_left_rail', 1515, -420, 675, 545, 36, 42, (0.722, 0.722, 0.722))
add_box('interior', 'front_left_seat_right_rail', 1515, -720, 675, 545, 36, 42, (0.722, 0.722, 0.722))
add_box('interior', 'rear_left_seat_left_rail', 2350, -420, 675, 545, 36, 42, (0.722, 0.722, 0.722))
add_box('interior', 'rear_left_seat_right_rail', 2350, -720, 675, 545, 36, 42, (0.722, 0.722, 0.722))
add_box('interior', 'left_front_seat_belt_buckle', 1730, -90, 850, 62, 42, 145, (0.839, 0.278, 0.216))
add_box('interior', 'left_front_seat_back_seam', 1848, -310, 1080, 24, 390, 28, (0.114, 0.114, 0.114))
add_box('interior', 'left_front_floor_mat', 1350, -310, 723, 760, 500, 22, (0.114, 0.114, 0.114))
add_box('interior', 'front_right_seat_left_rail', 1515, 420, 675, 545, 36, 42, (0.722, 0.722, 0.722))
add_box('interior', 'front_right_seat_right_rail', 1515, 720, 675, 545, 36, 42, (0.722, 0.722, 0.722))
add_box('interior', 'rear_right_seat_left_rail', 2350, 420, 675, 545, 36, 42, (0.722, 0.722, 0.722))
add_box('interior', 'rear_right_seat_right_rail', 2350, 720, 675, 545, 36, 42, (0.722, 0.722, 0.722))
add_box('interior', 'right_front_seat_belt_buckle', 1730, 90, 850, 62, 42, 145, (0.839, 0.278, 0.216))
add_box('interior', 'right_front_seat_back_seam', 1848, 310, 1080, 24, 390, 28, (0.114, 0.114, 0.114))
add_box('interior', 'right_front_floor_mat', 1350, 310, 723, 760, 500, 22, (0.114, 0.114, 0.114))
add_box('interior', 'rear_floor_mat', 2220, 0, 748, 1050, 1020, 22, (0.114, 0.114, 0.114))
add_box('interior', 'rear_bench_seat_seam', 2510, 0, 845, 610, 1010, 24, (0.114, 0.114, 0.114))
add_cylinder('engine_bay', 'cooling_fan_hub', 300, 0, 1010, 'x', 135, 62, (0.722, 0.722, 0.722))
add_box('engine_bay', 'cooling_fan_blade_1', 286, 210, 992, 38, 250, 36, (0.722, 0.722, 0.722))
add_box('engine_bay', 'cooling_fan_blade_2', 286, 105, 1173.87, 38, 250, 36, (0.722, 0.722, 0.722))
add_box('engine_bay', 'cooling_fan_blade_3', 286, -105, 1173.87, 38, 250, 36, (0.722, 0.722, 0.722))
add_box('engine_bay', 'cooling_fan_blade_4', 286, -210, 992, 38, 250, 36, (0.722, 0.722, 0.722))
add_box('engine_bay', 'cooling_fan_blade_5', 286, -105, 810.135, 38, 250, 36, (0.722, 0.722, 0.722))
add_box('engine_bay', 'cooling_fan_blade_6', 286, 105, 810.135, 38, 250, 36, (0.722, 0.722, 0.722))
add_cylinder('engine_bay', 'crank_pulley', 385, 0, 850, 'x', 145, 60, (0.722, 0.722, 0.722))
add_cylinder('engine_bay', 'water_pump_pulley', 360, 0, 1010, 'x', 125, 54, (0.722, 0.722, 0.722))
add_box('engine_bay', 'fan_belt_upper_run', 350, 0, 1010, 26, 38, 270, (0.114, 0.114, 0.114))
add_box('engine_bay', 'fan_belt_lower_run', 385, 0, 850, 26, 38, 235, (0.114, 0.114, 0.114))
add_cylinder('engine_bay', 'alternator_body', 565, 325, 1010, 'x', 190, 220, (0.722, 0.722, 0.722))
add_cylinder('engine_bay', 'starter_motor', 730, 265, 680, 'x', 155, 310, (0.722, 0.722, 0.722))
add_box('engine_bay', 'intake_manifold', 560, -260, 995, 460, 90, 115, (0.722, 0.722, 0.722))
add_box('engine_bay', 'exhaust_manifold', 575, 260, 900, 500, 95, 145, (0.247, 0.259, 0.271))
add_cylinder('engine_bay', 'carburetor_body', 745, -220, 1165, 'z', 120, 170, (0.722, 0.722, 0.722))
add_cylinder('engine_bay', 'round_air_cleaner_lid', 760, -235, 1250, 'z', 260, 68, (0.722, 0.722, 0.722))
add_cylinder('engine_bay', 'brake_booster', 1075, 520, 1060, 'x', 260, 145, (0.722, 0.722, 0.722))
add_cylinder('engine_bay', 'master_cylinder', 945, 520, 1060, 'x', 92, 230, (0.722, 0.722, 0.722))
add_box('engine_bay', 'clutch_master_cylinder', 945, 350, 1035, 210, 82, 76, (0.722, 0.722, 0.722))
add_box('engine_bay', 'rhd_firewall_pedal_box_outer_plate', 1112, 475, 895, 42, 350, 300, (0.722, 0.722, 0.722))
add_box('engine_bay', 'brake_booster_firewall_bracket', 1110, 520, 1015, 48, 300, 250, (0.722, 0.722, 0.722))
add_cylinder('engine_bay', 'brake_master_reservoir', 875, 520, 1165, 'z', 110, 105, (0.910, 0.910, 0.910))
add_cylinder('engine_bay', 'brake_master_reservoir_cap', 875, 520, 1225, 'z', 82, 24, (0.769, 0.604, 0.239))
add_cylinder('engine_bay', 'brake_booster_vacuum_hose', 820, 430, 1130, 'x', 34, 470, (0.114, 0.114, 0.114))
add_cylinder('engine_bay', 'clutch_master_reservoir_cap', 910, 350, 1130, 'z', 70, 26, (0.769, 0.604, 0.239))
add_cylinder('engine_bay', 'clutch_hydraulic_line_firewall_run', 830, 350, 980, 'x', 14, 520, (0.722, 0.722, 0.722))
add_cylinder('engine_bay', 'steering_column_lower_firewall_shaft', 1010, 420, 980, 'x', 44, 340, (0.722, 0.722, 0.722))
add_cylinder('engine_bay', 'steering_column_lower_universal_joint', 840, 430, 955, 'x', 76, 58, (0.722, 0.722, 0.722))
add_cylinder('engine_bay', 'steering_intermediate_shaft', 690, 455, 850, 'x', 40, 360, (0.722, 0.722, 0.722))
add_box('engine_bay', 'battery_case', 570, 430, 765, 310, 205, 205, (0.114, 0.114, 0.114))
add_cylinder('engine_bay', 'battery_positive_terminal', 622, 355, 985, 'z', 34, 46, (0.839, 0.278, 0.216))
add_cylinder('engine_bay', 'battery_negative_terminal', 812, 505, 985, 'z', 34, 46, (0.722, 0.722, 0.722))
add_cylinder('engine_bay', 'positive_battery_cable_run', 710, 405, 1015, 'x', 24, 520, (0.839, 0.278, 0.216))
add_cylinder('engine_bay', 'radiator_top_tank', 205, 0, 1095, 'y', 95, 1030, (0.722, 0.722, 0.722))
add_cylinder('engine_bay', 'radiator_bottom_tank', 205, 0, 720, 'y', 85, 1030, (0.722, 0.722, 0.722))
add_cylinder('engine_bay', 'radiator_cap', 218, 260, 1155, 'z', 54, 36, (0.769, 0.604, 0.239))
add_box('engine_bay', 'washer_bottle', 795, 535, 850, 160, 105, 210, (0.910, 0.910, 0.910))
add_box('engine_bay', 'engine_bay_fuse_relay_board_reference', 930, 610, 930, 240, 75, 220, (0.839, 0.278, 0.216))
add_cylinder('engine_bay', 'dipstick_loop', 840, 130, 1030, 'z', 46, 28, (0.769, 0.604, 0.239))
add_box('fuel_system', 'rear_underfloor_fuel_tank', 2870, 0, 405, 650, 930, 260, (0.310, 0.498, 0.333))
add_box('fuel_system', 'fuel_tank_retaining_strap_1', 2780, 0, 555, 42, 980, 38, (0.722, 0.722, 0.722))
add_box('fuel_system', 'fuel_tank_retaining_strap_2', 3020, 0, 555, 42, 980, 38, (0.722, 0.722, 0.722))
add_cylinder('fuel_system', 'fuel_filler_neck', 3000, -690, 940, 'z', 76, 410, (0.722, 0.722, 0.722))
add_cylinder('fuel_system', 'fuel_line_frame_run', 1880, 330, 560, 'x', 16, 2070, (0.769, 0.604, 0.239))
add_cylinder('exhaust', 'front_exhaust_pipe', 870, 310, 520, 'x', 68, 950, (0.722, 0.722, 0.722))
add_cylinder('exhaust', 'centre_exhaust_pipe', 1700, 330, 470, 'x', 68, 1020, (0.722, 0.722, 0.722))
add_cylinder('exhaust', 'rear_exhaust_pipe', 2750, 330, 470, 'x', 62, 1220, (0.722, 0.722, 0.722))
add_cylinder('exhaust', 'muffler_body', 2260, 330, 465, 'x', 250, 650, (0.722, 0.722, 0.722))
add_box('exhaust', 'exhaust_hanger_1', 1020, 330, 590, 52, 58, 135, (0.114, 0.114, 0.114))
add_box('exhaust', 'exhaust_hanger_2', 2180, 330, 590, 52, 58, 135, (0.114, 0.114, 0.114))
add_box('exhaust', 'exhaust_hanger_3', 3040, 330, 590, 52, 58, 135, (0.114, 0.114, 0.114))
add_cylinder('as_fitted_routes', 'j40_rt_001_drive_and_drivetrain_orientation_engine_gearbox_transfer_centerline', 1640, 0, 642, 'x', 20, 2600, (0.486, 0.435, 0.796))
add_cylinder('as_fitted_routes', 'j40_rt_001_drive_and_drivetrain_orientation_front_output_to_front_pinion', 1188, -82, 468, 'x', 20, 920, (0.486, 0.435, 0.796))
add_cylinder('as_fitted_routes', 'j40_rt_001_drive_and_drivetrain_orientation_rear_output_to_rear_pinion', 2235, 70, 468, 'x', 20, 1430, (0.486, 0.435, 0.796))
add_cylinder('as_fitted_routes', 'j40_rt_002_battery_positive_to_cutoff_battery_to_cutoff_sweep', 735, 432, 1032, 'x', 28, 430, (0.839, 0.278, 0.216))
add_cylinder('as_fitted_routes', 'j40_rt_003_cutoff_output_to_relay_box_feed_cutoff_to_relay_feed', 850, 540, 1040, 'x', 24, 430, (0.839, 0.278, 0.216))
add_cylinder('as_fitted_routes', 'j40_rt_004_cutoff_output_to_midi_common_feed_cutoff_to_midi_common', 860, 624, 980, 'x', 26, 470, (0.839, 0.278, 0.216))
add_cylinder('as_fitted_routes', 'j40_rt_005_midi_five_output_fanout_midi_output_fanout', 1030, 670, 950, 'y', 18, 360, (0.839, 0.278, 0.216))
add_cylinder('as_fitted_routes', 'j40_rt_006_battery_negative_engine_chassis_body_grounds_battery_negative_to_engine', 695, 310, 930, 'x', 24, 520, (0.722, 0.722, 0.722))
add_cylinder('as_fitted_routes', 'j40_rt_006_battery_negative_engine_chassis_body_grounds_body_chassis_ground_strap', 1115, 520, 760, 'z', 22, 280, (0.722, 0.722, 0.722))
add_cylinder('as_fitted_routes', 'j40_rt_007_starter_main_and_solenoid_trigger_starter_main_cable', 720, 286, 760, 'x', 24, 550, (0.839, 0.278, 0.216))
add_cylinder('as_fitted_routes', 'j40_rt_007_starter_main_and_solenoid_trigger_starter_solenoid_trigger', 780, 236, 820, 'x', 12, 460, (0.839, 0.278, 0.216))
add_cylinder('as_fitted_routes', 'j40_rt_008_alternator_charge_regulator_branch_alternator_charge_branch', 625, 325, 1065, 'x', 20, 590, (0.839, 0.278, 0.216))
add_cylinder('as_fitted_routes', 'j40_rt_009_engine_sender_injection_pump_branch_engine_sender_injection_pump_branch', 745, -165, 1085, 'x', 16, 760, (0.839, 0.278, 0.216))
add_cylinder('as_fitted_routes', 'j40_rt_010_headlamp_marker_horn_aux_lamp_branch_front_lamp_cross_loom', 145, 0, 735, 'y', 18, 1280, (0.839, 0.278, 0.216))
add_cylinder('as_fitted_routes', 'j40_rt_011_compressor_clutch_pressure_switch_condenser_fan_branch_compressor_pressure_fan_branch', 500, 485, 970, 'x', 16, 720, (0.839, 0.278, 0.216))
add_cylinder('as_fitted_routes', 'j40_rt_012_under_dash_evaporator_blower_controls_feed_under_dash_evaporator_feed', 1230, -420, 985, 'y', 18, 520, (0.839, 0.278, 0.216))
add_cylinder('as_fitted_routes', 'j40_rt_013_firewall_main_pass_throughs_main_firewall_pass_through_band', 1120, 0, 995, 'y', 22, 1160, (0.482, 0.353, 0.227))
add_cylinder('as_fitted_routes', 'j40_rt_014_rear_body_tail_fuel_sender_loom_rear_body_tail_fuel_sender_loom', 2835, -520, 700, 'x', 18, 1160, (0.839, 0.278, 0.216))
add_cylinder('as_fitted_routes', 'j40_rt_015_front_brake_hard_lines_and_flex_hoses_front_brake_master_to_crossmember', 980, 338, 650, 'x', 16, 920, (0.227, 0.471, 0.761))
add_cylinder('as_fitted_routes', 'j40_rt_015_front_brake_hard_lines_and_flex_hoses_front_brake_flex_sweep_left', 820, -650, 580, 'y', 20, 250, (0.227, 0.471, 0.761))
add_cylinder('as_fitted_routes', 'j40_rt_015_front_brake_hard_lines_and_flex_hoses_front_brake_flex_sweep_right', 820, 650, 580, 'y', 20, 250, (0.227, 0.471, 0.761))
add_cylinder('as_fitted_routes', 'j40_rt_016_rear_axle_hard_lines_center_flex_and_wheel_cylinder_lines_rear_axle_brake_pipe_and_center_flex', 3020, 0, 548, 'y', 18, 1330, (0.227, 0.471, 0.761))
add_cylinder('as_fitted_routes', 'j40_rt_017_parking_brake_cables_equalizer_and_clips_parking_brake_equalizer_to_axle', 2505, 0, 568, 'x', 22, 980, (0.482, 0.353, 0.227))
add_cylinder('as_fitted_routes', 'j40_rt_018_fuel_supply_return_leakoff_and_sender_routes_fuel_supply_return_frame_pair', 1880, 306, 542, 'x', 18, 2100, (0.227, 0.471, 0.761))
add_cylinder('as_fitted_routes', 'j40_rt_019_filler_neck_vent_and_tank_access_filler_neck_and_vent_pair', 3000, -650, 865, 'z', 42, 440, (0.227, 0.471, 0.761))
add_cylinder('as_fitted_routes', 'j40_rt_020_compressor_discharge_to_condenser_ac_discharge_compressor_to_condenser', 470, 535, 1080, 'x', 24, 680, (0.227, 0.471, 0.761))
add_cylinder('as_fitted_routes', 'j40_rt_021_condenser_to_receiver_drier_liquid_line_ac_condenser_to_drier_liquid_line', 330, -520, 915, 'y', 18, 930, (0.227, 0.471, 0.761))
add_cylinder('as_fitted_routes', 'j40_rt_022_drier_to_evaporator_and_evaporator_suction_to_compressor_ac_firewall_to_evaporator_suction_pair', 980, -420, 1035, 'x', 26, 650, (0.227, 0.471, 0.761))
add_cylinder('as_fitted_routes', 'j40_rt_023_radiator_heater_overflow_and_bypass_hoses_radiator_heater_overflow_hose_bundle', 395, -230, 1075, 'x', 38, 620, (0.227, 0.471, 0.761))
add_cylinder('as_fitted_routes', 'j40_rt_024_throttle_choke_fuel_stop_and_heater_control_cables_throttle_choke_fuel_stop_control_cables', 1050, 350, 915, 'x', 18, 560, (0.482, 0.353, 0.227))
add_cylinder('as_fitted_routes', 'j40_rt_025_speedometer_cable_and_transfer_gear_route_speedometer_cable_cluster_to_transfer', 1460, 235, 820, 'x', 18, 780, (0.482, 0.353, 0.227))
add_cylinder('as_fitted_routes', 'j40_rt_026_evaporator_condensate_and_body_drain_routes_evaporator_condensate_drain', 1235, -555, 660, 'z', 24, 430, (0.227, 0.471, 0.761))
add_cylinder('as_fitted_routes', 'j40_rt_027_exhaust_route_and_hanger_clearance_exhaust_heat_route_reference', 1910, 330, 610, 'x', 36, 2260, (0.710, 0.588, 0.890))
add_cylinder('as_fitted_routes', 'j40_rt_028_p_clips_tabs_grommets_and_loom_guards_routing_supports_spine', 1860, 430, 620, 'x', 14, 2240, (0.851, 0.835, 0.784))
add_box('as_fitted_routes', 'j40_rt_028_p_clips_tabs_grommets_and_loom_guards_shared_route_support_1_clip', 650, 430, 620, 42, 34, 34, (0.722, 0.722, 0.722))
add_box('as_fitted_routes', 'j40_rt_028_p_clips_tabs_grommets_and_loom_guards_shared_route_support_2_clip', 930, 430, 620, 42, 34, 34, (0.722, 0.722, 0.722))
add_box('as_fitted_routes', 'j40_rt_028_p_clips_tabs_grommets_and_loom_guards_shared_route_support_3_clip', 1210, 430, 620, 42, 34, 34, (0.722, 0.722, 0.722))
add_box('as_fitted_routes', 'j40_rt_028_p_clips_tabs_grommets_and_loom_guards_shared_route_support_4_clip', 1510, 430, 620, 42, 34, 34, (0.722, 0.722, 0.722))
add_box('as_fitted_routes', 'j40_rt_028_p_clips_tabs_grommets_and_loom_guards_shared_route_support_5_clip', 1830, 430, 620, 42, 34, 34, (0.722, 0.722, 0.722))
add_box('as_fitted_routes', 'j40_rt_028_p_clips_tabs_grommets_and_loom_guards_shared_route_support_6_clip', 2160, 430, 620, 42, 34, 34, (0.722, 0.722, 0.722))
add_box('as_fitted_routes', 'j40_rt_028_p_clips_tabs_grommets_and_loom_guards_shared_route_support_7_clip', 2480, 430, 620, 42, 34, 34, (0.722, 0.722, 0.722))
add_box('as_fitted_routes', 'j40_rt_028_p_clips_tabs_grommets_and_loom_guards_shared_route_support_8_clip', 2800, 430, 620, 42, 34, 34, (0.722, 0.722, 0.722))
add_box('as_fitted_routes', 'j40_rt_028_p_clips_tabs_grommets_and_loom_guards_shared_route_support_9_clip', 3130, 430, 620, 42, 34, 34, (0.722, 0.722, 0.722))
add_box('mechanical_clearance', 'fan_radiator_clearance_envelope', 275, 0, 990, 150, 720, 510, (0.710, 0.588, 0.890))
add_box('mechanical_clearance', 'front_steering_lock_sweep_left', 755, -705, 500, 420, 260, 250, (0.710, 0.588, 0.890))
add_box('mechanical_clearance', 'front_steering_lock_sweep_right', 755, 705, 500, 420, 260, 250, (0.710, 0.588, 0.890))
add_box('mechanical_clearance', 'front_prop_shaft_clearance_tunnel', 1120, 0, 438, 980, 260, 210, (0.710, 0.588, 0.890))
add_box('mechanical_clearance', 'rear_prop_shaft_clearance_tunnel', 2180, 0, 438, 1480, 280, 220, (0.710, 0.588, 0.890))
add_box('mechanical_clearance', 'pedal_column_hvac_clearance_zone', 1215, 420, 900, 420, 390, 420, (0.710, 0.588, 0.890))
add_cylinder('datum', 'wheelbase_datum_line_left', 1877.5, -925, 285, 'x', 18, 2285, (0.486, 0.435, 0.796))
add_cylinder('datum', 'wheelbase_datum_line_right', 1877.5, 925, 285, 'x', 18, 2285, (0.486, 0.435, 0.796))
add_cylinder('datum', 'front_track_datum_line', 735, 0, 260, 'y', 18, 1410, (0.486, 0.435, 0.796))
add_cylinder('datum', 'rear_track_datum_line', 3020, 0, 260, 'y', 18, 1410, (0.486, 0.435, 0.796))
add_cylinder('datum', 'cooling_pipe_fabrication_samples_main_run_datum', 505, -235, 1145, 'x', 30, 520, (0.486, 0.435, 0.796))
add_cylinder('datum', 'cooling_pipe_fabrication_samples_vertical_leg_datum', 360, -235, 995, 'z', 30, 315, (0.486, 0.435, 0.796))
add_cylinder('datum', 'cooling_pipe_fabrication_samples_upper_hose_overlap_datum', 245, -235, 1160, 'x', 42, 185, (0.486, 0.435, 0.796))
add_cylinder('datum', 'cooling_pipe_fabrication_samples_lower_hose_overlap_datum', 330, -235, 835, 'x', 42, 165, (0.486, 0.435, 0.796))
add_box('datum', 'cooling_pipe_fabrication_samples_clamp_pair_datum', 286, -235, 1000, 34, 84, 365, (0.486, 0.435, 0.796))
add_box('datum', 'radiator_sample_measurement_core_envelope', 205, 0, 915, 90, 1030, 430, (0.486, 0.435, 0.796))
add_cylinder('datum', 'front_support_radiator_measurement_set_lower_pickup_bar', 190, 0, 625, 'y', 18, 890, (0.486, 0.435, 0.796))
add_cylinder('datum', 'front_support_radiator_pickups_context_upper_pickup_bar', 188, 0, 1190, 'y', 18, 840, (0.486, 0.435, 0.796))
add_box('datum', 'existing_battery_mount_tray_measurements_tray_footprint', 575, 430, 640, 360, 250, 36, (0.486, 0.435, 0.796))
add_cylinder('datum', 'existing_battery_mount_tray_measurements_hold_down_span', 575, 430, 1005, 'y', 16, 250, (0.486, 0.435, 0.796))
add_cylinder('datum', 'installed_battery_dimension_reference_length_bar', 570, 300, 900, 'x', 16, 330, (0.486, 0.435, 0.796))
add_cylinder('datum', 'installed_battery_dimension_reference_width_bar', 735, 430, 900, 'y', 16, 225, (0.486, 0.435, 0.796))
add_cylinder('datum', 'installed_battery_dimension_reference_height_bar', 745, 560, 875, 'z', 16, 225, (0.486, 0.435, 0.796))
add_box('datum', 'suspension_bump_stop_removed_samples_front_envelope', 640, -560, 330, 125, 90, 86, (0.486, 0.435, 0.796))
add_box('datum', 'suspension_bump_stop_removed_samples_rear_envelope', 2925, -560, 330, 125, 90, 86, (0.486, 0.435, 0.796))
add_cylinder('datum', 'suspension_bump_stop_removed_samples_mount_hole_spacing_bar', 640, -560, 392, 'x', 14, 86, (0.486, 0.435, 0.796))

doc.recompute()
Gui.SendMsgToActiveView('ViewFit') if Gui is not None else None
