# J40 full vehicle CAD scaffold Rev B
# Units: millimetres. Run inside FreeCAD.
# Left-hand drive: negative Y is the driver side.
# Generated by tools/generate_j40_full_vehicle_cad_scaffold.py.
import FreeCAD as App
import Part
import Mesh

try:
    import FreeCADGui as Gui
except Exception:
    Gui = None

doc = App.newDocument('j40_full_vehicle_scaffold_rev_b')
groups = {}

TRANSPARENCY_BY_GROUP = {
    'glass': 60,
    'hard_top': 18,
    'datum': 45,
}

def group_for(group_name):
    group = groups.get(group_name)
    if group is None:
        group = doc.addObject('App::DocumentObjectGroup', group_name)
        group.Label = group_name.replace('_', ' ').title()
        groups[group_name] = group
    return group

def set_color(obj, rgb, group_name):
    if hasattr(obj, 'ViewObject'):
        obj.ViewObject.ShapeColor = rgb
        obj.ViewObject.Transparency = TRANSPARENCY_BY_GROUP.get(group_name, 0)

def add_to_group(obj, group_name):
    group_for(group_name).addObject(obj)
    return obj

def add_box(group_name, name, x, y_center, z, length, width, height, rgb):
    shape = Part.makeBox(length, width, height, App.Vector(x, y_center - width / 2, z))
    obj = doc.addObject('Part::Feature', name)
    obj.Shape = shape
    obj.Label = name.replace('_', ' ')
    set_color(obj, rgb, group_name)
    return add_to_group(obj, group_name)

def add_cylinder(group_name, name, x, y, z, axis, diameter, length, rgb):
    if axis == 'x':
        vector = App.Vector(1, 0, 0)
        base = App.Vector(x - length / 2, y, z)
    elif axis == 'y':
        vector = App.Vector(0, 1, 0)
        base = App.Vector(x, y - length / 2, z)
    else:
        vector = App.Vector(0, 0, 1)
        base = App.Vector(x, y, z - length / 2)
    obj = doc.addObject('Part::Feature', name)
    obj.Shape = Part.makeCylinder(diameter / 2, length, base, vector)
    obj.Label = name.replace('_', ' ')
    set_color(obj, rgb, group_name)
    return add_to_group(obj, group_name)

def add_wheel(group_name, name, x, y_center, z, diameter, width):
    tire = doc.addObject('Part::Feature', name + '_tire')
    tire.Shape = Part.makeCylinder(diameter / 2, width, App.Vector(x, y_center - width / 2, z), App.Vector(0, 1, 0))
    tire.Label = name.replace('_', ' ') + ' tire'
    set_color(tire, (0.03, 0.03, 0.03), group_name)
    add_to_group(tire, group_name)
    rim = doc.addObject('Part::Feature', name + '_rim')
    rim.Shape = Part.makeCylinder(diameter * 0.26, width + 8, App.Vector(x, y_center - (width + 8) / 2, z), App.Vector(0, 1, 0))
    rim.Label = name.replace('_', ' ') + ' rim'
    set_color(rim, (0.72, 0.72, 0.72), group_name)
    add_to_group(rim, group_name)
    hub = doc.addObject('Part::Feature', name + '_hub')
    hub.Shape = Part.makeCylinder(diameter * 0.15, width + 14, App.Vector(x, y_center - (width + 14) / 2, z), App.Vector(0, 1, 0))
    hub.Label = name.replace('_', ' ') + ' hub'
    set_color(hub, (0.10, 0.10, 0.10), group_name)
    add_to_group(hub, group_name)
    return tire

def add_mesh(group_name, name, vertices, faces, rgb):
    mesh = Mesh.Mesh()
    for face in faces:
        if len(face) < 3:
            continue
        first = App.Vector(*vertices[face[0]])
        for index in range(1, len(face) - 1):
            mesh.addFacet(first, App.Vector(*vertices[face[index]]), App.Vector(*vertices[face[index + 1]]))
    obj = doc.addObject('Mesh::Feature', name)
    obj.Mesh = mesh
    obj.Label = name.replace('_', ' ')
    set_color(obj, rgb, group_name)
    return add_to_group(obj, group_name)

add_box('chassis', 'left_frame_rail', 360, -390, 430, 3140, 85, 120, (0.176, 0.188, 0.200))
add_box('chassis', 'right_frame_rail', 360, 390, 430, 3140, 85, 120, (0.176, 0.188, 0.200))
add_box('chassis', 'crossmember_1', 450, 0, 455, 85, 880, 95, (0.176, 0.188, 0.200))
add_box('chassis', 'crossmember_2', 980, 0, 455, 85, 880, 95, (0.176, 0.188, 0.200))
add_box('chassis', 'crossmember_3', 1660, 0, 455, 85, 880, 95, (0.176, 0.188, 0.200))
add_box('chassis', 'crossmember_4', 2420, 0, 455, 85, 880, 95, (0.176, 0.188, 0.200))
add_box('chassis', 'crossmember_5', 3230, 0, 455, 85, 880, 95, (0.176, 0.188, 0.200))
add_box('chassis', 'front_bumper', 20, 0, 525, 165, 1620, 120, (0.067, 0.075, 0.082))
add_box('chassis', 'rear_bumper', 3665, 0, 530, 145, 1550, 110, (0.067, 0.075, 0.082))
add_cylinder('chassis', 'front_left_tow_ring', 75, -430, 450, 'x', 115, 28, (0.722, 0.722, 0.722))
add_cylinder('chassis', 'front_right_tow_ring', 75, 430, 450, 'x', 115, 28, (0.722, 0.722, 0.722))
add_box('running_gear', 'front_axle_tube', 735, 0, 395, 90, 1560, 90, (0.722, 0.722, 0.722))
add_box('running_gear', 'rear_axle_tube', 3020, 0, 395, 90, 1560, 90, (0.722, 0.722, 0.722))
add_box('running_gear', 'front_left_leaf_spring', 215, -430, 335, 1050, 65, 55, (0.133, 0.133, 0.133))
add_box('running_gear', 'front_right_leaf_spring', 215, 430, 335, 1050, 65, 55, (0.133, 0.133, 0.133))
add_box('running_gear', 'rear_left_leaf_spring', 2500, -430, 335, 1050, 65, 55, (0.133, 0.133, 0.133))
add_box('running_gear', 'rear_right_leaf_spring', 2500, 430, 335, 1050, 65, 55, (0.133, 0.133, 0.133))
add_wheel('running_gear', 'front_left_tire', 735, -705, 395, 790, 250)
add_wheel('running_gear', 'front_right_tire', 735, 705, 395, 790, 250)
add_wheel('running_gear', 'rear_left_tire', 3020, -705, 395, 790, 250)
add_wheel('running_gear', 'rear_right_tire', 3020, 705, 395, 790, 250)
add_box('running_gear', 'front_left_mud_tire_outer_lug_1', 1110, -705, 395, 95, 48, 58, (0.114, 0.114, 0.114))
add_box('running_gear', 'front_left_mud_tire_outer_lug_2', 1081.45, -705, 538.506, 95, 48, 58, (0.114, 0.114, 0.114))
add_box('running_gear', 'front_left_mud_tire_outer_lug_3', 1000.17, -705, 660.165, 95, 48, 58, (0.114, 0.114, 0.114))
add_box('running_gear', 'front_left_mud_tire_outer_lug_4', 878.506, -705, 741.455, 95, 48, 58, (0.114, 0.114, 0.114))
add_box('running_gear', 'front_left_mud_tire_outer_lug_5', 735, -705, 770, 95, 48, 58, (0.114, 0.114, 0.114))
add_box('running_gear', 'front_left_mud_tire_outer_lug_6', 591.494, -705, 741.455, 95, 48, 58, (0.114, 0.114, 0.114))
add_box('running_gear', 'front_left_mud_tire_outer_lug_7', 469.835, -705, 660.165, 95, 48, 58, (0.114, 0.114, 0.114))
add_box('running_gear', 'front_left_mud_tire_outer_lug_8', 388.545, -705, 538.506, 95, 48, 58, (0.114, 0.114, 0.114))
add_box('running_gear', 'front_left_mud_tire_outer_lug_9', 360, -705, 395, 95, 48, 58, (0.114, 0.114, 0.114))
add_box('running_gear', 'front_left_mud_tire_outer_lug_10', 388.545, -705, 251.494, 95, 48, 58, (0.114, 0.114, 0.114))
add_box('running_gear', 'front_left_mud_tire_outer_lug_11', 469.835, -705, 129.835, 95, 48, 58, (0.114, 0.114, 0.114))
add_box('running_gear', 'front_left_mud_tire_outer_lug_12', 591.494, -705, 48.5452, 95, 48, 58, (0.114, 0.114, 0.114))
add_box('running_gear', 'front_left_mud_tire_outer_lug_13', 735, -705, 20, 95, 48, 58, (0.114, 0.114, 0.114))
add_box('running_gear', 'front_left_mud_tire_outer_lug_14', 878.506, -705, 48.5452, 95, 48, 58, (0.114, 0.114, 0.114))
add_box('running_gear', 'front_left_mud_tire_outer_lug_15', 1000.17, -705, 129.835, 95, 48, 58, (0.114, 0.114, 0.114))
add_box('running_gear', 'front_left_mud_tire_outer_lug_16', 1081.45, -705, 251.494, 95, 48, 58, (0.114, 0.114, 0.114))
add_box('running_gear', 'front_right_mud_tire_outer_lug_1', 1110, 705, 395, 95, 48, 58, (0.114, 0.114, 0.114))
add_box('running_gear', 'front_right_mud_tire_outer_lug_2', 1081.45, 705, 538.506, 95, 48, 58, (0.114, 0.114, 0.114))
add_box('running_gear', 'front_right_mud_tire_outer_lug_3', 1000.17, 705, 660.165, 95, 48, 58, (0.114, 0.114, 0.114))
add_box('running_gear', 'front_right_mud_tire_outer_lug_4', 878.506, 705, 741.455, 95, 48, 58, (0.114, 0.114, 0.114))
add_box('running_gear', 'front_right_mud_tire_outer_lug_5', 735, 705, 770, 95, 48, 58, (0.114, 0.114, 0.114))
add_box('running_gear', 'front_right_mud_tire_outer_lug_6', 591.494, 705, 741.455, 95, 48, 58, (0.114, 0.114, 0.114))
add_box('running_gear', 'front_right_mud_tire_outer_lug_7', 469.835, 705, 660.165, 95, 48, 58, (0.114, 0.114, 0.114))
add_box('running_gear', 'front_right_mud_tire_outer_lug_8', 388.545, 705, 538.506, 95, 48, 58, (0.114, 0.114, 0.114))
add_box('running_gear', 'front_right_mud_tire_outer_lug_9', 360, 705, 395, 95, 48, 58, (0.114, 0.114, 0.114))
add_box('running_gear', 'front_right_mud_tire_outer_lug_10', 388.545, 705, 251.494, 95, 48, 58, (0.114, 0.114, 0.114))
add_box('running_gear', 'front_right_mud_tire_outer_lug_11', 469.835, 705, 129.835, 95, 48, 58, (0.114, 0.114, 0.114))
add_box('running_gear', 'front_right_mud_tire_outer_lug_12', 591.494, 705, 48.5452, 95, 48, 58, (0.114, 0.114, 0.114))
add_box('running_gear', 'front_right_mud_tire_outer_lug_13', 735, 705, 20, 95, 48, 58, (0.114, 0.114, 0.114))
add_box('running_gear', 'front_right_mud_tire_outer_lug_14', 878.506, 705, 48.5452, 95, 48, 58, (0.114, 0.114, 0.114))
add_box('running_gear', 'front_right_mud_tire_outer_lug_15', 1000.17, 705, 129.835, 95, 48, 58, (0.114, 0.114, 0.114))
add_box('running_gear', 'front_right_mud_tire_outer_lug_16', 1081.45, 705, 251.494, 95, 48, 58, (0.114, 0.114, 0.114))
add_box('running_gear', 'rear_left_mud_tire_outer_lug_1', 3395, -705, 395, 95, 48, 58, (0.114, 0.114, 0.114))
add_box('running_gear', 'rear_left_mud_tire_outer_lug_2', 3366.45, -705, 538.506, 95, 48, 58, (0.114, 0.114, 0.114))
add_box('running_gear', 'rear_left_mud_tire_outer_lug_3', 3285.17, -705, 660.165, 95, 48, 58, (0.114, 0.114, 0.114))
add_box('running_gear', 'rear_left_mud_tire_outer_lug_4', 3163.51, -705, 741.455, 95, 48, 58, (0.114, 0.114, 0.114))
add_box('running_gear', 'rear_left_mud_tire_outer_lug_5', 3020, -705, 770, 95, 48, 58, (0.114, 0.114, 0.114))
add_box('running_gear', 'rear_left_mud_tire_outer_lug_6', 2876.49, -705, 741.455, 95, 48, 58, (0.114, 0.114, 0.114))
add_box('running_gear', 'rear_left_mud_tire_outer_lug_7', 2754.83, -705, 660.165, 95, 48, 58, (0.114, 0.114, 0.114))
add_box('running_gear', 'rear_left_mud_tire_outer_lug_8', 2673.55, -705, 538.506, 95, 48, 58, (0.114, 0.114, 0.114))
add_box('running_gear', 'rear_left_mud_tire_outer_lug_9', 2645, -705, 395, 95, 48, 58, (0.114, 0.114, 0.114))
add_box('running_gear', 'rear_left_mud_tire_outer_lug_10', 2673.55, -705, 251.494, 95, 48, 58, (0.114, 0.114, 0.114))
add_box('running_gear', 'rear_left_mud_tire_outer_lug_11', 2754.83, -705, 129.835, 95, 48, 58, (0.114, 0.114, 0.114))
add_box('running_gear', 'rear_left_mud_tire_outer_lug_12', 2876.49, -705, 48.5452, 95, 48, 58, (0.114, 0.114, 0.114))
add_box('running_gear', 'rear_left_mud_tire_outer_lug_13', 3020, -705, 20, 95, 48, 58, (0.114, 0.114, 0.114))
add_box('running_gear', 'rear_left_mud_tire_outer_lug_14', 3163.51, -705, 48.5452, 95, 48, 58, (0.114, 0.114, 0.114))
add_box('running_gear', 'rear_left_mud_tire_outer_lug_15', 3285.17, -705, 129.835, 95, 48, 58, (0.114, 0.114, 0.114))
add_box('running_gear', 'rear_left_mud_tire_outer_lug_16', 3366.45, -705, 251.494, 95, 48, 58, (0.114, 0.114, 0.114))
add_box('running_gear', 'rear_right_mud_tire_outer_lug_1', 3395, 705, 395, 95, 48, 58, (0.114, 0.114, 0.114))
add_box('running_gear', 'rear_right_mud_tire_outer_lug_2', 3366.45, 705, 538.506, 95, 48, 58, (0.114, 0.114, 0.114))
add_box('running_gear', 'rear_right_mud_tire_outer_lug_3', 3285.17, 705, 660.165, 95, 48, 58, (0.114, 0.114, 0.114))
add_box('running_gear', 'rear_right_mud_tire_outer_lug_4', 3163.51, 705, 741.455, 95, 48, 58, (0.114, 0.114, 0.114))
add_box('running_gear', 'rear_right_mud_tire_outer_lug_5', 3020, 705, 770, 95, 48, 58, (0.114, 0.114, 0.114))
add_box('running_gear', 'rear_right_mud_tire_outer_lug_6', 2876.49, 705, 741.455, 95, 48, 58, (0.114, 0.114, 0.114))
add_box('running_gear', 'rear_right_mud_tire_outer_lug_7', 2754.83, 705, 660.165, 95, 48, 58, (0.114, 0.114, 0.114))
add_box('running_gear', 'rear_right_mud_tire_outer_lug_8', 2673.55, 705, 538.506, 95, 48, 58, (0.114, 0.114, 0.114))
add_box('running_gear', 'rear_right_mud_tire_outer_lug_9', 2645, 705, 395, 95, 48, 58, (0.114, 0.114, 0.114))
add_box('running_gear', 'rear_right_mud_tire_outer_lug_10', 2673.55, 705, 251.494, 95, 48, 58, (0.114, 0.114, 0.114))
add_box('running_gear', 'rear_right_mud_tire_outer_lug_11', 2754.83, 705, 129.835, 95, 48, 58, (0.114, 0.114, 0.114))
add_box('running_gear', 'rear_right_mud_tire_outer_lug_12', 2876.49, 705, 48.5452, 95, 48, 58, (0.114, 0.114, 0.114))
add_box('running_gear', 'rear_right_mud_tire_outer_lug_13', 3020, 705, 20, 95, 48, 58, (0.114, 0.114, 0.114))
add_box('running_gear', 'rear_right_mud_tire_outer_lug_14', 3163.51, 705, 48.5452, 95, 48, 58, (0.114, 0.114, 0.114))
add_box('running_gear', 'rear_right_mud_tire_outer_lug_15', 3285.17, 705, 129.835, 95, 48, 58, (0.114, 0.114, 0.114))
add_box('running_gear', 'rear_right_mud_tire_outer_lug_16', 3366.45, 705, 251.494, 95, 48, 58, (0.114, 0.114, 0.114))
add_cylinder('running_gear', 'front_left_shock_body', 920, -520, 620, 'z', 58, 460, (0.722, 0.722, 0.722))
add_cylinder('running_gear', 'front_right_shock_body', 920, 520, 620, 'z', 58, 460, (0.722, 0.722, 0.722))
add_cylinder('running_gear', 'front_left_hub_cap', 735, -840, 395, 'y', 220, 80, (0.722, 0.722, 0.722))
add_cylinder('running_gear', 'front_right_hub_cap', 735, 840, 395, 'y', 220, 80, (0.722, 0.722, 0.722))
add_cylinder('running_gear', 'rear_left_shock_body', 3205, -520, 620, 'z', 58, 460, (0.722, 0.722, 0.722))
add_cylinder('running_gear', 'rear_right_shock_body', 3205, 520, 620, 'z', 58, 460, (0.722, 0.722, 0.722))
add_cylinder('running_gear', 'rear_left_hub_cap', 3020, -840, 395, 'y', 220, 80, (0.722, 0.722, 0.722))
add_cylinder('running_gear', 'rear_right_hub_cap', 3020, 840, 395, 'y', 220, 80, (0.722, 0.722, 0.722))
add_box('body', 'floor_pan', 890, 0, 615, 2550, 1330, 55, (0.812, 0.776, 0.667))
add_box('body', 'left_rocker_sill', 1000, -720, 665, 2050, 95, 155, (0.812, 0.776, 0.667))
add_box('body', 'right_rocker_sill', 1000, 720, 665, 2050, 95, 155, (0.812, 0.776, 0.667))
add_box('body', 'left_rear_quarter_panel', 2140, -760, 725, 1270, 70, 610, (0.812, 0.776, 0.667))
add_box('body', 'right_rear_quarter_panel', 2140, 760, 725, 1270, 70, 610, (0.812, 0.776, 0.667))
add_box('body', 'tailgate_panel', 3400, 0, 720, 70, 1430, 650, (0.812, 0.776, 0.667))
add_box('body', 'firewall', 1135, 0, 690, 80, 1420, 780, (0.812, 0.776, 0.667))
add_box('body', 'cowl_top', 1085, 0, 1260, 190, 1460, 110, (0.812, 0.776, 0.667))
add_box('body', 'grille_panel', 170, 0, 790, 80, 1410, 520, (0.812, 0.776, 0.667))
add_box('front_detail', 'white_grille_surround', 125, 0, 795, 35, 1120, 365, (0.910, 0.910, 0.910))
add_box('front_detail', 'black_grille_mesh', 105, 0, 910, 30, 640, 155, (0.114, 0.114, 0.114))
add_cylinder('front_detail', 'left_headlamp', 92, -445, 985, 'x', 225, 38, (0.910, 0.910, 0.910))
add_cylinder('front_detail', 'right_headlamp', 92, 445, 985, 'x', 225, 38, (0.910, 0.910, 0.910))
add_cylinder('front_detail', 'left_indicator_lamp', 84, -720, 845, 'x', 105, 30, (0.722, 0.482, 0.333))
add_cylinder('front_detail', 'right_indicator_lamp', 84, 720, 845, 'x', 105, 30, (0.722, 0.482, 0.333))
add_cylinder('front_detail', 'left_fog_lamp', 25, -360, 620, 'x', 165, 36, (0.910, 0.910, 0.910))
add_cylinder('front_detail', 'right_fog_lamp', 25, 360, 620, 'x', 165, 36, (0.910, 0.910, 0.910))
add_box('body', 'hood_closed_reference', 230, 0, 1215, 920, 1390, 38, (0.812, 0.776, 0.667))
add_mesh('body', 'hood_crowned_closed_skin', [(135, -642, 1230), (135, 0, 1256), (135, 642, 1230), (1058, -642, 1296), (1058, 0, 1322), (1058, 642, 1296), (135, -642, 1210), (135, 0, 1236), (135, 642, 1210), (1058, -642, 1276), (1058, 0, 1302), (1058, 642, 1276)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.812, 0.776, 0.667))
add_mesh('body', 'hood_front_rolled_lip_surface', [(96, -610, 1204), (96, 610, 1204), (150, 610, 1218), (150, -610, 1218), (96, -610, 1248), (96, 610, 1248), (150, 610, 1254), (150, -610, 1254)], [(0, 1, 2, 3), (4, 7, 6, 5), (0, 4, 5, 1), (1, 5, 6, 2), (2, 6, 7, 3), (3, 7, 4, 0)], (0.616, 0.588, 0.494))
add_cylinder('body', 'hood_left_hinge_axis', 1030, -540, 1288, 'y', 28, 230, (0.722, 0.722, 0.722))
add_cylinder('body', 'hood_right_hinge_axis', 1030, 540, 1288, 'y', 28, 230, (0.722, 0.722, 0.722))
add_box('body', 'left_front_fender', 270, -720, 760, 860, 270, 260, (0.812, 0.776, 0.667))
add_box('body', 'right_front_fender', 270, 720, 760, 860, 270, 260, (0.812, 0.776, 0.667))
add_box('body', 'left_inner_fender', 290, -520, 800, 800, 70, 420, (0.812, 0.776, 0.667))
add_box('body', 'right_inner_fender', 290, 520, 800, 800, 70, 420, (0.812, 0.776, 0.667))
add_box('body', 'windshield_frame', 1155, 0, 1315, 80, 1480, 520, (0.812, 0.776, 0.667))
add_box('body', 'windshield_glass', 1160, 0, 1380, 35, 1300, 410, (0.435, 0.647, 0.722))
add_cylinder('body', 'windshield_left_wiper', 1110, -250, 1370, 'y', 24, 430, (0.114, 0.114, 0.114))
add_cylinder('body', 'windshield_right_wiper', 1110, 250, 1370, 'y', 24, 430, (0.114, 0.114, 0.114))
add_box('hard_top', 'white_hardtop_roof', 1210, 0, 1838, 2290, 1540, 58, (0.945, 0.933, 0.894))
add_mesh('hard_top', 'white_hardtop_crowned_roof_skin', [(1125, -760, 1886), (1125, 0, 1932), (1125, 760, 1886), (3440, -760, 1896), (3440, 0, 1942), (3440, 760, 1896), (1125, -760, 1860), (1125, 0, 1906), (1125, 760, 1860), (3440, -760, 1870), (3440, 0, 1916), (3440, 760, 1870)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.945, 0.933, 0.894))
add_box('hard_top', 'left_hardtop_side_panel', 1240, -790, 1320, 2200, 55, 590, (0.812, 0.776, 0.667))
add_box('hard_top', 'right_hardtop_side_panel', 1240, 790, 1320, 2200, 55, 590, (0.812, 0.776, 0.667))
add_box('hard_top', 'left_front_hardtop_window', 1420, -823, 1435, 500, 20, 320, (0.435, 0.647, 0.722))
add_box('hard_top', 'left_rear_hardtop_window', 2190, -823, 1435, 610, 20, 320, (0.435, 0.647, 0.722))
add_box('hard_top', 'right_front_hardtop_window', 1420, 823, 1435, 500, 20, 320, (0.435, 0.647, 0.722))
add_box('hard_top', 'right_rear_hardtop_window', 2190, 823, 1435, 610, 20, 320, (0.435, 0.647, 0.722))
add_box('hard_top', 'rear_hardtop_panel', 3440, 0, 1320, 55, 1540, 590, (0.812, 0.776, 0.667))
add_box('hard_top', 'roof_front_gutter', 1160, 0, 1810, 70, 1575, 46, (0.945, 0.933, 0.894))
add_box('hard_top', 'roof_left_gutter', 2250, -830, 1815, 2200, 58, 42, (0.945, 0.933, 0.894))
add_box('hard_top', 'roof_right_gutter', 2250, 830, 1815, 2200, 58, 42, (0.945, 0.933, 0.894))
add_box('body', 'left_door_open_reference', 1180, -910, 760, 800, 70, 850, (0.812, 0.776, 0.667))
add_box('body', 'right_door_closed_reference', 1180, 760, 760, 800, 70, 850, (0.812, 0.776, 0.667))
add_box('body', 'left_door_window_glass', 1280, -948, 1210, 520, 22, 345, (0.435, 0.647, 0.722))
add_box('body', 'right_door_window_glass', 1280, 798, 1210, 520, 22, 345, (0.435, 0.647, 0.722))
add_cylinder('body', 'left_upper_door_hinge', 1135, -955, 1180, 'z', 38, 145, (0.722, 0.722, 0.722))
add_cylinder('body', 'left_lower_door_hinge', 1135, -955, 850, 'z', 38, 145, (0.722, 0.722, 0.722))
add_cylinder('body', 'right_upper_door_hinge', 1135, 805, 1180, 'z', 38, 145, (0.722, 0.722, 0.722))
add_cylinder('body', 'right_lower_door_hinge', 1135, 805, 850, 'z', 38, 145, (0.722, 0.722, 0.722))
add_box('body', 'left_door_handle', 1575, -955, 1045, 160, 30, 40, (0.722, 0.722, 0.722))
add_box('body', 'right_door_handle', 1575, 805, 1045, 160, 30, 40, (0.722, 0.722, 0.722))
add_box('engine_bay', 'engine_block', 460, 0, 720, 520, 420, 430, (0.247, 0.259, 0.271))
add_box('engine_bay', 'valve_cover', 510, 0, 1080, 460, 180, 70, (0.722, 0.722, 0.722))
add_box('engine_bay', 'radiator', 235, 0, 820, 75, 980, 520, (0.247, 0.259, 0.271))
add_box('engine_bay', 'air_filter', 760, -235, 1120, 210, 210, 150, (0.247, 0.259, 0.271))
add_box('engine_bay', 'battery_tray_reference', 600, 430, 760, 330, 220, 220, (0.910, 0.910, 0.910))
add_cylinder('engine_bay', 'inline_six_intake_stack_1', 470, -165, 1160, 'z', 46, 180, (0.722, 0.722, 0.722))
add_cylinder('engine_bay', 'inline_six_intake_stack_2', 470, -99, 1160, 'z', 46, 180, (0.722, 0.722, 0.722))
add_cylinder('engine_bay', 'inline_six_intake_stack_3', 470, -33, 1160, 'z', 46, 180, (0.722, 0.722, 0.722))
add_cylinder('engine_bay', 'inline_six_intake_stack_4', 470, 33, 1160, 'z', 46, 180, (0.722, 0.722, 0.722))
add_cylinder('engine_bay', 'inline_six_intake_stack_5', 470, 99, 1160, 'z', 46, 180, (0.722, 0.722, 0.722))
add_cylinder('engine_bay', 'inline_six_intake_stack_6', 470, 165, 1160, 'z', 46, 180, (0.722, 0.722, 0.722))
add_cylinder('engine_bay', 'upper_radiator_hose', 330, -185, 1110, 'x', 72, 430, (0.114, 0.114, 0.114))
add_cylinder('engine_bay', 'exhaust_downpipe_reference', 615, 255, 845, 'z', 82, 460, (0.722, 0.722, 0.722))
add_box('interior', 'dashboard', 1235, 0, 1080, 120, 1320, 220, (0.722, 0.482, 0.333))
add_box('interior', 'steering_column', 1135, -420, 935, 590, 60, 60, (0.722, 0.722, 0.722))
add_cylinder('interior', 'steering_wheel', 1240, -420, 1210, 'x', 380, 32, (0.114, 0.114, 0.114))
add_cylinder('interior', 'steering_wheel_hub', 1230, -420, 1210, 'x', 135, 55, (0.722, 0.722, 0.722))
add_cylinder('interior', 'dashboard_gauge_1', 1222, -560, 1175, 'x', 72, 24, (0.910, 0.910, 0.910))
add_cylinder('interior', 'dashboard_gauge_2', 1222, -470, 1175, 'x', 72, 24, (0.910, 0.910, 0.910))
add_cylinder('interior', 'dashboard_gauge_3', 1222, -380, 1175, 'x', 72, 24, (0.910, 0.910, 0.910))
add_cylinder('interior', 'dashboard_gauge_4', 1222, -290, 1175, 'x', 72, 24, (0.910, 0.910, 0.910))
add_cylinder('interior', 'transfer_case_lever', 1580, -120, 820, 'z', 36, 285, (0.722, 0.722, 0.722))
add_cylinder('interior', 'gearshift_lever', 1500, -35, 820, 'z', 38, 330, (0.722, 0.722, 0.722))
add_box('interior', 'front_left_seat_base', 1660, -310, 700, 420, 410, 130, (0.722, 0.482, 0.333))
add_box('interior', 'front_left_seat_back', 1850, -310, 820, 95, 410, 620, (0.722, 0.482, 0.333))
add_cylinder('interior', 'front_left_headrest', 1905, -310, 1435, 'y', 150, 300, (0.722, 0.482, 0.333))
add_box('interior', 'front_right_seat_base', 1660, 310, 700, 420, 410, 130, (0.722, 0.482, 0.333))
add_box('interior', 'front_right_seat_back', 1850, 310, 820, 95, 410, 620, (0.722, 0.482, 0.333))
add_cylinder('interior', 'front_right_headrest', 1905, 310, 1435, 'y', 150, 300, (0.722, 0.482, 0.333))
add_box('interior', 'rear_bench_base', 2510, 0, 720, 610, 1080, 135, (0.722, 0.482, 0.333))
add_box('interior', 'rear_bench_back', 2920, 0, 840, 105, 1080, 560, (0.722, 0.482, 0.333))
add_cylinder('interior', 'rear_bench_left_headrest', 2975, -350, 1390, 'y', 140, 270, (0.722, 0.482, 0.333))
add_cylinder('interior', 'rear_bench_right_headrest', 2975, 350, 1390, 'y', 140, 270, (0.722, 0.482, 0.333))
add_mesh('body', 'windshield_raked_glass_surface', [(1110, -602, 1378), (1110, 602, 1378), (1148, 602, 1378), (1148, -602, 1378), (1110, -602, 1722), (1110, 602, 1722), (1148, 602, 1700), (1148, -602, 1700)], [(0, 1, 2, 3), (4, 7, 6, 5), (0, 4, 5, 1), (1, 5, 6, 2), (2, 6, 7, 3), (3, 7, 4, 0)], (0.435, 0.647, 0.722))
add_mesh('front_detail', 'front_grille_inset_rounded_surround_surface', [(56, -585, 802), (56, 585, 802), (106, 585, 820), (106, -585, 820), (56, -585, 1125), (56, 585, 1125), (106, 585, 1100), (106, -585, 1100)], [(0, 1, 2, 3), (4, 7, 6, 5), (0, 4, 5, 1), (1, 5, 6, 2), (2, 6, 7, 3), (3, 7, 4, 0)], (0.910, 0.910, 0.910))
add_mesh('chassis', 'front_bumper_swept_main_face', [(-18, -760, 484), (-18, 760, 484), (92, 760, 520), (92, -760, 520), (-18, -760, 608), (-18, 760, 608), (92, 760, 620), (92, -760, 620)], [(0, 1, 2, 3), (4, 7, 6, 5), (0, 4, 5, 1), (1, 5, 6, 2), (2, 6, 7, 3), (3, 7, 4, 0)], (0.067, 0.075, 0.082))
add_mesh('chassis', 'rear_bumper_swept_main_face', [(3638, -730, 492), (3638, 730, 492), (3750, 730, 520), (3750, -730, 520), (3638, -730, 604), (3638, 730, 604), (3750, 730, 612), (3750, -730, 612)], [(0, 1, 2, 3), (4, 7, 6, 5), (0, 4, 5, 1), (1, 5, 6, 2), (2, 6, 7, 3), (3, 7, 4, 0)], (0.067, 0.075, 0.082))
add_mesh('hard_top', 'front_roof_header_overhang_skin', [(1092, -786, 1808), (1092, 0, 1834), (1092, 786, 1808), (1208, -786, 1852), (1208, 0, 1878), (1208, 786, 1852), (1092, -786, 1792), (1092, 0, 1818), (1092, 786, 1792), (1208, -786, 1836), (1208, 0, 1862), (1208, 786, 1836)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.945, 0.933, 0.894))
add_mesh('hard_top', 'rear_roof_overhang_skin', [(3360, -776, 1862), (3360, 0, 1890), (3360, 776, 1862), (3508, -776, 1848), (3508, 0, 1876), (3508, 776, 1848), (3360, -776, 1844), (3360, 0, 1872), (3360, 776, 1844), (3508, -776, 1830), (3508, 0, 1858), (3508, 776, 1830)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.945, 0.933, 0.894))
add_mesh('hard_top', 'rear_barn_door_left_subtle_crown', [(3484, -690, 920), (3484, -354, 938), (3484, -18, 920), (3534, -690, 924), (3534, -354, 942), (3534, -18, 924), (3484, -690, 904), (3484, -354, 922), (3484, -18, 904), (3534, -690, 908), (3534, -354, 926), (3534, -18, 908)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.812, 0.776, 0.667))
add_mesh('hard_top', 'rear_barn_door_right_subtle_crown', [(3484, 18, 920), (3484, 354, 938), (3484, 690, 920), (3534, 18, 924), (3534, 354, 942), (3534, 690, 924), (3484, 18, 904), (3484, 354, 922), (3484, 690, 904), (3534, 18, 908), (3534, 354, 926), (3534, 690, 908)], [(0, 3, 4, 1), (1, 4, 5, 2), (6, 7, 10, 9), (7, 8, 11, 10), (0, 1, 7, 6), (1, 2, 8, 7), (3, 9, 10, 4), (4, 10, 11, 5), (0, 6, 9, 3), (2, 5, 11, 8)], (0.812, 0.776, 0.667))
add_mesh('body', 'left_front_fender_sloped_outer_skin', [(118, -846, 706), (118, -646, 706), (1035, -646, 744), (1035, -846, 744), (118, -846, 1048), (118, -646, 1048), (1035, -646, 1242), (1035, -846, 1242)], [(0, 1, 2, 3), (4, 7, 6, 5), (0, 4, 5, 1), (1, 5, 6, 2), (2, 6, 7, 3), (3, 7, 4, 0)], (0.812, 0.776, 0.667))
add_mesh('chassis', 'left_front_bumper_swept_return', [(24, -846, 500), (24, -720, 500), (128, -720, 548), (128, -846, 548), (24, -846, 610), (24, -720, 610), (128, -720, 620), (128, -846, 620)], [(0, 1, 2, 3), (4, 7, 6, 5), (0, 4, 5, 1), (1, 5, 6, 2), (2, 6, 7, 3), (3, 7, 4, 0)], (0.067, 0.075, 0.082))
add_mesh('chassis', 'left_rear_bumper_swept_return', [(3628, -812, 502), (3628, -695, 502), (3735, -695, 540), (3735, -812, 540), (3628, -812, 604), (3628, -695, 604), (3735, -695, 612), (3735, -812, 612)], [(0, 1, 2, 3), (4, 7, 6, 5), (0, 4, 5, 1), (1, 5, 6, 2), (2, 6, 7, 3), (3, 7, 4, 0)], (0.067, 0.075, 0.082))
add_mesh('body', 'left_front_fender_rolled_upper_crown', [(155, -754, 1062), (155, -560, 1062), (1015, -560, 1238), (1015, -754, 1238), (155, -754, 1110), (155, -560, 1110), (1015, -560, 1268), (1015, -754, 1268)], [(0, 1, 2, 3), (4, 7, 6, 5), (0, 4, 5, 1), (1, 5, 6, 2), (2, 6, 7, 3), (3, 7, 4, 0)], (0.894, 0.863, 0.780))
add_mesh('body', 'left_cowl_side_blend_surface', [(960, -815, 1116), (960, -660, 1116), (1165, -660, 1214), (1165, -815, 1214), (960, -815, 1340), (960, -660, 1340), (1165, -660, 1410), (1165, -815, 1410)], [(0, 1, 2, 3), (4, 7, 6, 5), (0, 4, 5, 1), (1, 5, 6, 2), (2, 6, 7, 3), (3, 7, 4, 0)], (0.812, 0.776, 0.667))
add_mesh('body', 'left_door_outer_skin_tapered_surface', [(1128, -824, 748), (1128, -734, 748), (1938, -734, 748), (1938, -824, 748), (1128, -824, 1270), (1128, -734, 1270), (1938, -734, 1308), (1938, -824, 1308)], [(0, 1, 2, 3), (4, 7, 6, 5), (0, 4, 5, 1), (1, 5, 6, 2), (2, 6, 7, 3), (3, 7, 4, 0)], (0.812, 0.776, 0.667))
add_mesh('body', 'left_rear_quarter_waist_tapered_surface', [(1942, -830, 724), (1942, -730, 724), (3385, -730, 746), (3385, -830, 746), (1942, -830, 1305), (1942, -730, 1305), (3385, -730, 1278), (3385, -830, 1278)], [(0, 1, 2, 3), (4, 7, 6, 5), (0, 4, 5, 1), (1, 5, 6, 2), (2, 6, 7, 3), (3, 7, 4, 0)], (0.812, 0.776, 0.667))
add_mesh('hard_top', 'left_hardtop_side_tapered_upper_skin', [(1212, -820, 1308), (1212, -748, 1308), (3425, -748, 1300), (3425, -820, 1300), (1212, -820, 1790), (1212, -748, 1790), (3425, -748, 1782), (3425, -820, 1782)], [(0, 1, 2, 3), (4, 7, 6, 5), (0, 4, 5, 1), (1, 5, 6, 2), (2, 6, 7, 3), (3, 7, 4, 0)], (0.812, 0.776, 0.667))
add_mesh('hard_top', 'left_hardtop_lower_side_roll_surface', [(1225, -812, 1260), (1225, -742, 1260), (3415, -742, 1258), (3415, -812, 1258), (1225, -812, 1345), (1225, -742, 1345), (3415, -742, 1332), (3415, -812, 1332)], [(0, 1, 2, 3), (4, 7, 6, 5), (0, 4, 5, 1), (1, 5, 6, 2), (2, 6, 7, 3), (3, 7, 4, 0)], (0.616, 0.588, 0.494))
add_mesh('hard_top', 'left_hardtop_rear_corner_radius_facet', [(3365, -806, 1300), (3365, -650, 1300), (3470, -650, 1308), (3470, -806, 1308), (3365, -806, 1780), (3365, -650, 1780), (3470, -650, 1762), (3470, -806, 1762)], [(0, 1, 2, 3), (4, 7, 6, 5), (0, 4, 5, 1), (1, 5, 6, 2), (2, 6, 7, 3), (3, 7, 4, 0)], (0.616, 0.588, 0.494))
add_mesh('body', 'left_front_outer_arch_rounded_skin_facet_1', [(1015.74, -846, 700), (1015.74, -734, 700), (1087.74, -734, 700), (1087.74, -846, 700), (1015.74, -846, 625.5), (1015.74, -734, 625.5), (1087.74, -734, 625.5), (1087.74, -846, 625.5)], [(0, 1, 2, 3), (4, 7, 6, 5), (0, 4, 5, 1), (1, 5, 6, 2), (2, 6, 7, 3), (3, 7, 4, 0)], (0.812, 0.776, 0.667))
add_mesh('body', 'left_front_outer_arch_rounded_skin_facet_2', [(935.998, -846, 700), (935.998, -734, 700), (1008, -734, 700), (1008, -846, 700), (935.998, -846, 723.974), (935.998, -734, 723.974), (1008, -734, 723.974), (1008, -846, 723.974)], [(0, 1, 2, 3), (4, 7, 6, 5), (0, 4, 5, 1), (1, 5, 6, 2), (2, 6, 7, 3), (3, 7, 4, 0)], (0.812, 0.776, 0.667))
add_mesh('body', 'left_front_outer_arch_rounded_skin_facet_3', [(829.728, -846, 740.986), (829.728, -734, 740.986), (901.728, -734, 740.986), (901.728, -846, 740.986), (829.728, -846, 792.986), (829.728, -734, 792.986), (901.728, -734, 792.986), (901.728, -846, 792.986)], [(0, 1, 2, 3), (4, 7, 6, 5), (0, 4, 5, 1), (1, 5, 6, 2), (2, 6, 7, 3), (3, 7, 4, 0)], (0.812, 0.776, 0.667))
add_mesh('body', 'left_front_outer_arch_rounded_skin_facet_4', [(707.334, -846, 773.781), (707.334, -734, 773.781), (779.334, -734, 773.781), (779.334, -846, 773.781), (707.334, -846, 825.781), (707.334, -734, 825.781), (779.334, -734, 825.781), (779.334, -846, 825.781)], [(0, 1, 2, 3), (4, 7, 6, 5), (0, 4, 5, 1), (1, 5, 6, 2), (2, 6, 7, 3), (3, 7, 4, 0)], (0.812, 0.776, 0.667))
add_mesh('body', 'left_front_outer_arch_rounded_skin_facet_5', [(580.796, -846, 767.15), (580.796, -734, 767.15), (652.796, -734, 767.15), (652.796, -846, 767.15), (580.796, -846, 819.15), (580.796, -734, 819.15), (652.796, -734, 819.15), (652.796, -846, 819.15)], [(0, 1, 2, 3), (4, 7, 6, 5), (0, 4, 5, 1), (1, 5, 6, 2), (2, 6, 7, 3), (3, 7, 4, 0)], (0.812, 0.776, 0.667))
add_mesh('body', 'left_front_outer_arch_rounded_skin_facet_6', [(462.5, -846, 721.74), (462.5, -734, 721.74), (534.5, -734, 721.74), (534.5, -846, 721.74), (462.5, -846, 773.74), (462.5, -734, 773.74), (534.5, -734, 773.74), (534.5, -846, 773.74)], [(0, 1, 2, 3), (4, 7, 6, 5), (0, 4, 5, 1), (1, 5, 6, 2), (2, 6, 7, 3), (3, 7, 4, 0)], (0.812, 0.776, 0.667))
add_mesh('body', 'left_front_outer_arch_rounded_skin_facet_7', [(364.026, -846, 700), (364.026, -734, 700), (436.026, -734, 700), (436.026, -846, 700), (364.026, -846, 693.998), (364.026, -734, 693.998), (436.026, -734, 693.998), (436.026, -846, 693.998)], [(0, 1, 2, 3), (4, 7, 6, 5), (0, 4, 5, 1), (1, 5, 6, 2), (2, 6, 7, 3), (3, 7, 4, 0)], (0.812, 0.776, 0.667))
add_mesh('body', 'left_rear_outer_arch_rounded_skin_facet_1', [(3287.75, -846, 688), (3287.75, -734, 688), (3359.75, -734, 688), (3359.75, -846, 688), (3287.75, -846, 618), (3287.75, -734, 618), (3359.75, -734, 618), (3359.75, -846, 618)], [(0, 1, 2, 3), (4, 7, 6, 5), (0, 4, 5, 1), (1, 5, 6, 2), (2, 6, 7, 3), (3, 7, 4, 0)], (0.812, 0.776, 0.667))
add_mesh('body', 'left_rear_outer_arch_rounded_skin_facet_2', [(3210.96, -846, 688), (3210.96, -734, 688), (3282.96, -734, 688), (3282.96, -846, 688), (3210.96, -846, 712.826), (3210.96, -734, 712.826), (3282.96, -734, 712.826), (3282.96, -846, 712.826)], [(0, 1, 2, 3), (4, 7, 6, 5), (0, 4, 5, 1), (1, 5, 6, 2), (2, 6, 7, 3), (3, 7, 4, 0)], (0.812, 0.776, 0.667))
add_mesh('body', 'left_rear_outer_arch_rounded_skin_facet_3', [(3108.63, -846, 727.283), (3108.63, -734, 727.283), (3180.63, -734, 727.283), (3180.63, -846, 727.283), (3108.63, -846, 779.283), (3108.63, -734, 779.283), (3180.63, -734, 779.283), (3180.63, -846, 779.283)], [(0, 1, 2, 3), (4, 7, 6, 5), (0, 4, 5, 1), (1, 5, 6, 2), (2, 6, 7, 3), (3, 7, 4, 0)], (0.812, 0.776, 0.667))
add_mesh('body', 'left_rear_outer_arch_rounded_skin_facet_4', [(2990.77, -846, 758.864), (2990.77, -734, 758.864), (3062.77, -734, 758.864), (3062.77, -846, 758.864), (2990.77, -846, 810.864), (2990.77, -734, 810.864), (3062.77, -734, 810.864), (3062.77, -846, 810.864)], [(0, 1, 2, 3), (4, 7, 6, 5), (0, 4, 5, 1), (1, 5, 6, 2), (2, 6, 7, 3), (3, 7, 4, 0)], (0.812, 0.776, 0.667))
add_mesh('body', 'left_rear_outer_arch_rounded_skin_facet_5', [(2868.91, -846, 752.478), (2868.91, -734, 752.478), (2940.91, -734, 752.478), (2940.91, -846, 752.478), (2868.91, -846, 804.478), (2868.91, -734, 804.478), (2940.91, -734, 804.478), (2940.91, -846, 804.478)], [(0, 1, 2, 3), (4, 7, 6, 5), (0, 4, 5, 1), (1, 5, 6, 2), (2, 6, 7, 3), (3, 7, 4, 0)], (0.812, 0.776, 0.667))
add_mesh('body', 'left_rear_outer_arch_rounded_skin_facet_6', [(2755, -846, 708.75), (2755, -734, 708.75), (2827, -734, 708.75), (2827, -846, 708.75), (2755, -846, 760.75), (2755, -734, 760.75), (2827, -734, 760.75), (2827, -846, 760.75)], [(0, 1, 2, 3), (4, 7, 6, 5), (0, 4, 5, 1), (1, 5, 6, 2), (2, 6, 7, 3), (3, 7, 4, 0)], (0.812, 0.776, 0.667))
add_mesh('body', 'left_rear_outer_arch_rounded_skin_facet_7', [(2660.17, -846, 688), (2660.17, -734, 688), (2732.17, -734, 688), (2732.17, -846, 688), (2660.17, -846, 683.961), (2660.17, -734, 683.961), (2732.17, -734, 683.961), (2732.17, -846, 683.961)], [(0, 1, 2, 3), (4, 7, 6, 5), (0, 4, 5, 1), (1, 5, 6, 2), (2, 6, 7, 3), (3, 7, 4, 0)], (0.812, 0.776, 0.667))
add_mesh('body', 'right_front_fender_sloped_outer_skin', [(118, 646, 706), (118, 846, 706), (1035, 846, 744), (1035, 646, 744), (118, 646, 1048), (118, 846, 1048), (1035, 846, 1242), (1035, 646, 1242)], [(0, 1, 2, 3), (4, 7, 6, 5), (0, 4, 5, 1), (1, 5, 6, 2), (2, 6, 7, 3), (3, 7, 4, 0)], (0.812, 0.776, 0.667))
add_mesh('chassis', 'right_front_bumper_swept_return', [(24, 720, 500), (24, 846, 500), (128, 846, 548), (128, 720, 548), (24, 720, 610), (24, 846, 610), (128, 846, 620), (128, 720, 620)], [(0, 1, 2, 3), (4, 7, 6, 5), (0, 4, 5, 1), (1, 5, 6, 2), (2, 6, 7, 3), (3, 7, 4, 0)], (0.067, 0.075, 0.082))
add_mesh('chassis', 'right_rear_bumper_swept_return', [(3628, 695, 502), (3628, 812, 502), (3735, 812, 540), (3735, 695, 540), (3628, 695, 604), (3628, 812, 604), (3735, 812, 612), (3735, 695, 612)], [(0, 1, 2, 3), (4, 7, 6, 5), (0, 4, 5, 1), (1, 5, 6, 2), (2, 6, 7, 3), (3, 7, 4, 0)], (0.067, 0.075, 0.082))
add_mesh('body', 'right_front_fender_rolled_upper_crown', [(155, 560, 1062), (155, 754, 1062), (1015, 754, 1238), (1015, 560, 1238), (155, 560, 1110), (155, 754, 1110), (1015, 754, 1268), (1015, 560, 1268)], [(0, 1, 2, 3), (4, 7, 6, 5), (0, 4, 5, 1), (1, 5, 6, 2), (2, 6, 7, 3), (3, 7, 4, 0)], (0.894, 0.863, 0.780))
add_mesh('body', 'right_cowl_side_blend_surface', [(960, 660, 1116), (960, 815, 1116), (1165, 815, 1214), (1165, 660, 1214), (960, 660, 1340), (960, 815, 1340), (1165, 815, 1410), (1165, 660, 1410)], [(0, 1, 2, 3), (4, 7, 6, 5), (0, 4, 5, 1), (1, 5, 6, 2), (2, 6, 7, 3), (3, 7, 4, 0)], (0.812, 0.776, 0.667))
add_mesh('body', 'right_door_outer_skin_tapered_surface', [(1128, 734, 748), (1128, 824, 748), (1938, 824, 748), (1938, 734, 748), (1128, 734, 1270), (1128, 824, 1270), (1938, 824, 1308), (1938, 734, 1308)], [(0, 1, 2, 3), (4, 7, 6, 5), (0, 4, 5, 1), (1, 5, 6, 2), (2, 6, 7, 3), (3, 7, 4, 0)], (0.812, 0.776, 0.667))
add_mesh('body', 'right_rear_quarter_waist_tapered_surface', [(1942, 730, 724), (1942, 830, 724), (3385, 830, 746), (3385, 730, 746), (1942, 730, 1305), (1942, 830, 1305), (3385, 830, 1278), (3385, 730, 1278)], [(0, 1, 2, 3), (4, 7, 6, 5), (0, 4, 5, 1), (1, 5, 6, 2), (2, 6, 7, 3), (3, 7, 4, 0)], (0.812, 0.776, 0.667))
add_mesh('hard_top', 'right_hardtop_side_tapered_upper_skin', [(1212, 748, 1308), (1212, 820, 1308), (3425, 820, 1300), (3425, 748, 1300), (1212, 748, 1790), (1212, 820, 1790), (3425, 820, 1782), (3425, 748, 1782)], [(0, 1, 2, 3), (4, 7, 6, 5), (0, 4, 5, 1), (1, 5, 6, 2), (2, 6, 7, 3), (3, 7, 4, 0)], (0.812, 0.776, 0.667))
add_mesh('hard_top', 'right_hardtop_lower_side_roll_surface', [(1225, 742, 1260), (1225, 812, 1260), (3415, 812, 1258), (3415, 742, 1258), (1225, 742, 1345), (1225, 812, 1345), (3415, 812, 1332), (3415, 742, 1332)], [(0, 1, 2, 3), (4, 7, 6, 5), (0, 4, 5, 1), (1, 5, 6, 2), (2, 6, 7, 3), (3, 7, 4, 0)], (0.616, 0.588, 0.494))
add_mesh('hard_top', 'right_hardtop_rear_corner_radius_facet', [(3365, 650, 1300), (3365, 806, 1300), (3470, 806, 1308), (3470, 650, 1308), (3365, 650, 1780), (3365, 806, 1780), (3470, 806, 1762), (3470, 650, 1762)], [(0, 1, 2, 3), (4, 7, 6, 5), (0, 4, 5, 1), (1, 5, 6, 2), (2, 6, 7, 3), (3, 7, 4, 0)], (0.616, 0.588, 0.494))
add_mesh('body', 'right_front_outer_arch_rounded_skin_facet_1', [(1015.74, 734, 700), (1015.74, 846, 700), (1087.74, 846, 700), (1087.74, 734, 700), (1015.74, 734, 625.5), (1015.74, 846, 625.5), (1087.74, 846, 625.5), (1087.74, 734, 625.5)], [(0, 1, 2, 3), (4, 7, 6, 5), (0, 4, 5, 1), (1, 5, 6, 2), (2, 6, 7, 3), (3, 7, 4, 0)], (0.812, 0.776, 0.667))
add_mesh('body', 'right_front_outer_arch_rounded_skin_facet_2', [(935.998, 734, 700), (935.998, 846, 700), (1008, 846, 700), (1008, 734, 700), (935.998, 734, 723.974), (935.998, 846, 723.974), (1008, 846, 723.974), (1008, 734, 723.974)], [(0, 1, 2, 3), (4, 7, 6, 5), (0, 4, 5, 1), (1, 5, 6, 2), (2, 6, 7, 3), (3, 7, 4, 0)], (0.812, 0.776, 0.667))
add_mesh('body', 'right_front_outer_arch_rounded_skin_facet_3', [(829.728, 734, 740.986), (829.728, 846, 740.986), (901.728, 846, 740.986), (901.728, 734, 740.986), (829.728, 734, 792.986), (829.728, 846, 792.986), (901.728, 846, 792.986), (901.728, 734, 792.986)], [(0, 1, 2, 3), (4, 7, 6, 5), (0, 4, 5, 1), (1, 5, 6, 2), (2, 6, 7, 3), (3, 7, 4, 0)], (0.812, 0.776, 0.667))
add_mesh('body', 'right_front_outer_arch_rounded_skin_facet_4', [(707.334, 734, 773.781), (707.334, 846, 773.781), (779.334, 846, 773.781), (779.334, 734, 773.781), (707.334, 734, 825.781), (707.334, 846, 825.781), (779.334, 846, 825.781), (779.334, 734, 825.781)], [(0, 1, 2, 3), (4, 7, 6, 5), (0, 4, 5, 1), (1, 5, 6, 2), (2, 6, 7, 3), (3, 7, 4, 0)], (0.812, 0.776, 0.667))
add_mesh('body', 'right_front_outer_arch_rounded_skin_facet_5', [(580.796, 734, 767.15), (580.796, 846, 767.15), (652.796, 846, 767.15), (652.796, 734, 767.15), (580.796, 734, 819.15), (580.796, 846, 819.15), (652.796, 846, 819.15), (652.796, 734, 819.15)], [(0, 1, 2, 3), (4, 7, 6, 5), (0, 4, 5, 1), (1, 5, 6, 2), (2, 6, 7, 3), (3, 7, 4, 0)], (0.812, 0.776, 0.667))
add_mesh('body', 'right_front_outer_arch_rounded_skin_facet_6', [(462.5, 734, 721.74), (462.5, 846, 721.74), (534.5, 846, 721.74), (534.5, 734, 721.74), (462.5, 734, 773.74), (462.5, 846, 773.74), (534.5, 846, 773.74), (534.5, 734, 773.74)], [(0, 1, 2, 3), (4, 7, 6, 5), (0, 4, 5, 1), (1, 5, 6, 2), (2, 6, 7, 3), (3, 7, 4, 0)], (0.812, 0.776, 0.667))
add_mesh('body', 'right_front_outer_arch_rounded_skin_facet_7', [(364.026, 734, 700), (364.026, 846, 700), (436.026, 846, 700), (436.026, 734, 700), (364.026, 734, 693.998), (364.026, 846, 693.998), (436.026, 846, 693.998), (436.026, 734, 693.998)], [(0, 1, 2, 3), (4, 7, 6, 5), (0, 4, 5, 1), (1, 5, 6, 2), (2, 6, 7, 3), (3, 7, 4, 0)], (0.812, 0.776, 0.667))
add_mesh('body', 'right_rear_outer_arch_rounded_skin_facet_1', [(3287.75, 734, 688), (3287.75, 846, 688), (3359.75, 846, 688), (3359.75, 734, 688), (3287.75, 734, 618), (3287.75, 846, 618), (3359.75, 846, 618), (3359.75, 734, 618)], [(0, 1, 2, 3), (4, 7, 6, 5), (0, 4, 5, 1), (1, 5, 6, 2), (2, 6, 7, 3), (3, 7, 4, 0)], (0.812, 0.776, 0.667))
add_mesh('body', 'right_rear_outer_arch_rounded_skin_facet_2', [(3210.96, 734, 688), (3210.96, 846, 688), (3282.96, 846, 688), (3282.96, 734, 688), (3210.96, 734, 712.826), (3210.96, 846, 712.826), (3282.96, 846, 712.826), (3282.96, 734, 712.826)], [(0, 1, 2, 3), (4, 7, 6, 5), (0, 4, 5, 1), (1, 5, 6, 2), (2, 6, 7, 3), (3, 7, 4, 0)], (0.812, 0.776, 0.667))
add_mesh('body', 'right_rear_outer_arch_rounded_skin_facet_3', [(3108.63, 734, 727.283), (3108.63, 846, 727.283), (3180.63, 846, 727.283), (3180.63, 734, 727.283), (3108.63, 734, 779.283), (3108.63, 846, 779.283), (3180.63, 846, 779.283), (3180.63, 734, 779.283)], [(0, 1, 2, 3), (4, 7, 6, 5), (0, 4, 5, 1), (1, 5, 6, 2), (2, 6, 7, 3), (3, 7, 4, 0)], (0.812, 0.776, 0.667))
add_mesh('body', 'right_rear_outer_arch_rounded_skin_facet_4', [(2990.77, 734, 758.864), (2990.77, 846, 758.864), (3062.77, 846, 758.864), (3062.77, 734, 758.864), (2990.77, 734, 810.864), (2990.77, 846, 810.864), (3062.77, 846, 810.864), (3062.77, 734, 810.864)], [(0, 1, 2, 3), (4, 7, 6, 5), (0, 4, 5, 1), (1, 5, 6, 2), (2, 6, 7, 3), (3, 7, 4, 0)], (0.812, 0.776, 0.667))
add_mesh('body', 'right_rear_outer_arch_rounded_skin_facet_5', [(2868.91, 734, 752.478), (2868.91, 846, 752.478), (2940.91, 846, 752.478), (2940.91, 734, 752.478), (2868.91, 734, 804.478), (2868.91, 846, 804.478), (2940.91, 846, 804.478), (2940.91, 734, 804.478)], [(0, 1, 2, 3), (4, 7, 6, 5), (0, 4, 5, 1), (1, 5, 6, 2), (2, 6, 7, 3), (3, 7, 4, 0)], (0.812, 0.776, 0.667))
add_mesh('body', 'right_rear_outer_arch_rounded_skin_facet_6', [(2755, 734, 708.75), (2755, 846, 708.75), (2827, 846, 708.75), (2827, 734, 708.75), (2755, 734, 760.75), (2755, 846, 760.75), (2827, 846, 760.75), (2827, 734, 760.75)], [(0, 1, 2, 3), (4, 7, 6, 5), (0, 4, 5, 1), (1, 5, 6, 2), (2, 6, 7, 3), (3, 7, 4, 0)], (0.812, 0.776, 0.667))
add_mesh('body', 'right_rear_outer_arch_rounded_skin_facet_7', [(2660.17, 734, 688), (2660.17, 846, 688), (2732.17, 846, 688), (2732.17, 734, 688), (2660.17, 734, 683.961), (2660.17, 846, 683.961), (2732.17, 846, 683.961), (2732.17, 734, 683.961)], [(0, 1, 2, 3), (4, 7, 6, 5), (0, 4, 5, 1), (1, 5, 6, 2), (2, 6, 7, 3), (3, 7, 4, 0)], (0.812, 0.776, 0.667))
add_box('chassis', 'left_front_frame_horn_top_plate', 120, -390, 555, 500, 95, 24, (0.176, 0.188, 0.200))
add_box('chassis', 'left_front_frame_horn_side_web', 120, -448, 440, 500, 18, 150, (0.176, 0.188, 0.200))
add_box('chassis', 'left_rear_frame_horn_top_plate', 3230, -390, 555, 420, 95, 24, (0.176, 0.188, 0.200))
add_box('chassis', 'left_rear_frame_horn_side_web', 3230, -448, 440, 420, 18, 145, (0.176, 0.188, 0.200))
add_box('chassis', 'left_body_mount_outrigger_1', 740, -525, 525, 280, 70, 55, (0.176, 0.188, 0.200))
add_cylinder('chassis', 'left_body_mount_rubber_biscuit_1', 965, -615, 610, 'z', 118, 42, (0.114, 0.114, 0.114))
add_cylinder('chassis', 'left_body_mount_center_bolt_1', 965, -615, 632, 'z', 30, 70, (0.722, 0.722, 0.722))
add_box('chassis', 'left_body_mount_outrigger_2', 1135, -525, 525, 280, 70, 55, (0.176, 0.188, 0.200))
add_cylinder('chassis', 'left_body_mount_rubber_biscuit_2', 1360, -615, 610, 'z', 118, 42, (0.114, 0.114, 0.114))
add_cylinder('chassis', 'left_body_mount_center_bolt_2', 1360, -615, 632, 'z', 30, 70, (0.722, 0.722, 0.722))
add_box('chassis', 'left_body_mount_outrigger_3', 1610, -525, 525, 280, 70, 55, (0.176, 0.188, 0.200))
add_cylinder('chassis', 'left_body_mount_rubber_biscuit_3', 1835, -615, 610, 'z', 118, 42, (0.114, 0.114, 0.114))
add_cylinder('chassis', 'left_body_mount_center_bolt_3', 1835, -615, 632, 'z', 30, 70, (0.722, 0.722, 0.722))
add_box('chassis', 'left_body_mount_outrigger_4', 2250, -525, 525, 280, 70, 55, (0.176, 0.188, 0.200))
add_cylinder('chassis', 'left_body_mount_rubber_biscuit_4', 2475, -615, 610, 'z', 118, 42, (0.114, 0.114, 0.114))
add_cylinder('chassis', 'left_body_mount_center_bolt_4', 2475, -615, 632, 'z', 30, 70, (0.722, 0.722, 0.722))
add_box('chassis', 'left_body_mount_outrigger_5', 2920, -525, 525, 280, 70, 55, (0.176, 0.188, 0.200))
add_cylinder('chassis', 'left_body_mount_rubber_biscuit_5', 3145, -615, 610, 'z', 118, 42, (0.114, 0.114, 0.114))
add_cylinder('chassis', 'left_body_mount_center_bolt_5', 3145, -615, 632, 'z', 30, 70, (0.722, 0.722, 0.722))
add_box('chassis', 'left_front_fixed_spring_hanger_outer_plate', 210, -475, 360, 105, 28, 180, (0.176, 0.188, 0.200))
add_box('chassis', 'left_front_fixed_spring_hanger_inner_plate', 210, -390, 360, 105, 28, 180, (0.176, 0.188, 0.200))
add_cylinder('chassis', 'left_front_fixed_spring_pin', 262, -432.5, 430, 'y', 42, 130, (0.722, 0.722, 0.722))
add_box('chassis', 'left_front_shackle_spring_hanger_outer_plate', 1280, -475, 360, 105, 28, 180, (0.176, 0.188, 0.200))
add_box('chassis', 'left_front_shackle_spring_hanger_inner_plate', 1280, -390, 360, 105, 28, 180, (0.176, 0.188, 0.200))
add_cylinder('chassis', 'left_front_shackle_spring_pin', 1332, -432.5, 430, 'y', 42, 130, (0.722, 0.722, 0.722))
add_box('chassis', 'left_rear_fixed_spring_hanger_outer_plate', 2495, -475, 360, 105, 28, 180, (0.176, 0.188, 0.200))
add_box('chassis', 'left_rear_fixed_spring_hanger_inner_plate', 2495, -390, 360, 105, 28, 180, (0.176, 0.188, 0.200))
add_cylinder('chassis', 'left_rear_fixed_spring_pin', 2547, -432.5, 430, 'y', 42, 130, (0.722, 0.722, 0.722))
add_box('chassis', 'left_rear_shackle_spring_hanger_outer_plate', 3565, -475, 360, 105, 28, 180, (0.176, 0.188, 0.200))
add_box('chassis', 'left_rear_shackle_spring_hanger_inner_plate', 3565, -390, 360, 105, 28, 180, (0.176, 0.188, 0.200))
add_cylinder('chassis', 'left_rear_shackle_spring_pin', 3617, -432.5, 430, 'y', 42, 130, (0.722, 0.722, 0.722))
add_box('chassis', 'left_crossmember_1_gusset_front', 898, -390, 465, 38, 230, 90, (0.176, 0.188, 0.200))
add_box('chassis', 'left_crossmember_1_gusset_rear', 1106, -390, 465, 38, 230, 90, (0.176, 0.188, 0.200))
add_box('chassis', 'left_crossmember_2_gusset_front', 1578, -390, 465, 38, 230, 90, (0.176, 0.188, 0.200))
add_box('chassis', 'left_crossmember_2_gusset_rear', 1786, -390, 465, 38, 230, 90, (0.176, 0.188, 0.200))
add_box('chassis', 'left_crossmember_3_gusset_front', 2338, -390, 465, 38, 230, 90, (0.176, 0.188, 0.200))
add_box('chassis', 'left_crossmember_3_gusset_rear', 2546, -390, 465, 38, 230, 90, (0.176, 0.188, 0.200))
add_box('running_gear', 'left_front_upper_shock_mount', 945, -575, 875, 115, 110, 135, (0.176, 0.188, 0.200))
add_box('running_gear', 'left_rear_upper_shock_mount', 3185, -575, 875, 115, 110, 135, (0.176, 0.188, 0.200))
add_cylinder('running_gear', 'left_front_shock_piston_rod', 920, -520, 850, 'z', 24, 280, (0.722, 0.722, 0.722))
add_cylinder('running_gear', 'left_rear_shock_piston_rod', 3205, -520, 850, 'z', 24, 280, (0.722, 0.722, 0.722))
add_box('running_gear', 'left_front_bump_stop', 640, -495, 540, 115, 80, 72, (0.114, 0.114, 0.114))
add_box('running_gear', 'left_rear_bump_stop', 2925, -495, 540, 115, 80, 72, (0.114, 0.114, 0.114))
add_box('chassis', 'right_front_frame_horn_top_plate', 120, 390, 555, 500, 95, 24, (0.176, 0.188, 0.200))
add_box('chassis', 'right_front_frame_horn_side_web', 120, 448, 440, 500, 18, 150, (0.176, 0.188, 0.200))
add_box('chassis', 'right_rear_frame_horn_top_plate', 3230, 390, 555, 420, 95, 24, (0.176, 0.188, 0.200))
add_box('chassis', 'right_rear_frame_horn_side_web', 3230, 448, 440, 420, 18, 145, (0.176, 0.188, 0.200))
add_box('chassis', 'right_body_mount_outrigger_1', 740, 525, 525, 280, 70, 55, (0.176, 0.188, 0.200))
add_cylinder('chassis', 'right_body_mount_rubber_biscuit_1', 965, 615, 610, 'z', 118, 42, (0.114, 0.114, 0.114))
add_cylinder('chassis', 'right_body_mount_center_bolt_1', 965, 615, 632, 'z', 30, 70, (0.722, 0.722, 0.722))
add_box('chassis', 'right_body_mount_outrigger_2', 1135, 525, 525, 280, 70, 55, (0.176, 0.188, 0.200))
add_cylinder('chassis', 'right_body_mount_rubber_biscuit_2', 1360, 615, 610, 'z', 118, 42, (0.114, 0.114, 0.114))
add_cylinder('chassis', 'right_body_mount_center_bolt_2', 1360, 615, 632, 'z', 30, 70, (0.722, 0.722, 0.722))
add_box('chassis', 'right_body_mount_outrigger_3', 1610, 525, 525, 280, 70, 55, (0.176, 0.188, 0.200))
add_cylinder('chassis', 'right_body_mount_rubber_biscuit_3', 1835, 615, 610, 'z', 118, 42, (0.114, 0.114, 0.114))
add_cylinder('chassis', 'right_body_mount_center_bolt_3', 1835, 615, 632, 'z', 30, 70, (0.722, 0.722, 0.722))
add_box('chassis', 'right_body_mount_outrigger_4', 2250, 525, 525, 280, 70, 55, (0.176, 0.188, 0.200))
add_cylinder('chassis', 'right_body_mount_rubber_biscuit_4', 2475, 615, 610, 'z', 118, 42, (0.114, 0.114, 0.114))
add_cylinder('chassis', 'right_body_mount_center_bolt_4', 2475, 615, 632, 'z', 30, 70, (0.722, 0.722, 0.722))
add_box('chassis', 'right_body_mount_outrigger_5', 2920, 525, 525, 280, 70, 55, (0.176, 0.188, 0.200))
add_cylinder('chassis', 'right_body_mount_rubber_biscuit_5', 3145, 615, 610, 'z', 118, 42, (0.114, 0.114, 0.114))
add_cylinder('chassis', 'right_body_mount_center_bolt_5', 3145, 615, 632, 'z', 30, 70, (0.722, 0.722, 0.722))
add_box('chassis', 'right_front_fixed_spring_hanger_outer_plate', 210, 475, 360, 105, 28, 180, (0.176, 0.188, 0.200))
add_box('chassis', 'right_front_fixed_spring_hanger_inner_plate', 210, 390, 360, 105, 28, 180, (0.176, 0.188, 0.200))
add_cylinder('chassis', 'right_front_fixed_spring_pin', 262, 432.5, 430, 'y', 42, 130, (0.722, 0.722, 0.722))
add_box('chassis', 'right_front_shackle_spring_hanger_outer_plate', 1280, 475, 360, 105, 28, 180, (0.176, 0.188, 0.200))
add_box('chassis', 'right_front_shackle_spring_hanger_inner_plate', 1280, 390, 360, 105, 28, 180, (0.176, 0.188, 0.200))
add_cylinder('chassis', 'right_front_shackle_spring_pin', 1332, 432.5, 430, 'y', 42, 130, (0.722, 0.722, 0.722))
add_box('chassis', 'right_rear_fixed_spring_hanger_outer_plate', 2495, 475, 360, 105, 28, 180, (0.176, 0.188, 0.200))
add_box('chassis', 'right_rear_fixed_spring_hanger_inner_plate', 2495, 390, 360, 105, 28, 180, (0.176, 0.188, 0.200))
add_cylinder('chassis', 'right_rear_fixed_spring_pin', 2547, 432.5, 430, 'y', 42, 130, (0.722, 0.722, 0.722))
add_box('chassis', 'right_rear_shackle_spring_hanger_outer_plate', 3565, 475, 360, 105, 28, 180, (0.176, 0.188, 0.200))
add_box('chassis', 'right_rear_shackle_spring_hanger_inner_plate', 3565, 390, 360, 105, 28, 180, (0.176, 0.188, 0.200))
add_cylinder('chassis', 'right_rear_shackle_spring_pin', 3617, 432.5, 430, 'y', 42, 130, (0.722, 0.722, 0.722))
add_box('chassis', 'right_crossmember_1_gusset_front', 898, 390, 465, 38, 230, 90, (0.176, 0.188, 0.200))
add_box('chassis', 'right_crossmember_1_gusset_rear', 1106, 390, 465, 38, 230, 90, (0.176, 0.188, 0.200))
add_box('chassis', 'right_crossmember_2_gusset_front', 1578, 390, 465, 38, 230, 90, (0.176, 0.188, 0.200))
add_box('chassis', 'right_crossmember_2_gusset_rear', 1786, 390, 465, 38, 230, 90, (0.176, 0.188, 0.200))
add_box('chassis', 'right_crossmember_3_gusset_front', 2338, 390, 465, 38, 230, 90, (0.176, 0.188, 0.200))
add_box('chassis', 'right_crossmember_3_gusset_rear', 2546, 390, 465, 38, 230, 90, (0.176, 0.188, 0.200))
add_box('running_gear', 'right_front_upper_shock_mount', 945, 575, 875, 115, 110, 135, (0.176, 0.188, 0.200))
add_box('running_gear', 'right_rear_upper_shock_mount', 3185, 575, 875, 115, 110, 135, (0.176, 0.188, 0.200))
add_cylinder('running_gear', 'right_front_shock_piston_rod', 920, 520, 850, 'z', 24, 280, (0.722, 0.722, 0.722))
add_cylinder('running_gear', 'right_rear_shock_piston_rod', 3205, 520, 850, 'z', 24, 280, (0.722, 0.722, 0.722))
add_box('running_gear', 'right_front_bump_stop', 640, 495, 540, 115, 80, 72, (0.114, 0.114, 0.114))
add_box('running_gear', 'right_rear_bump_stop', 2925, 495, 540, 115, 80, 72, (0.114, 0.114, 0.114))
add_box('chassis', 'transfer_case_crossmember', 1710, 0, 500, 260, 940, 120, (0.176, 0.188, 0.200))
add_box('chassis', 'skid_plate_transfer_case', 1600, 0, 315, 520, 620, 42, (0.722, 0.722, 0.722))
add_box('running_gear', 'transfer_case', 1640, 0, 575, 410, 360, 265, (0.247, 0.259, 0.271))
add_box('running_gear', 'gearbox_tail_housing', 1325, 0, 610, 430, 300, 260, (0.247, 0.259, 0.271))
add_cylinder('running_gear', 'front_prop_shaft', 1120, 0, 465, 'x', 82, 900, (0.722, 0.722, 0.722))
add_cylinder('running_gear', 'rear_prop_shaft', 2180, 0, 465, 'x', 82, 1360, (0.722, 0.722, 0.722))
add_cylinder('running_gear', 'front_diff_pumpkin', 735, 0, 420, 'y', 360, 300, (0.722, 0.722, 0.722))
add_cylinder('running_gear', 'rear_diff_pumpkin', 3020, 0, 420, 'y', 380, 320, (0.722, 0.722, 0.722))
add_cylinder('running_gear', 'front_pinion_nose', 920, 0, 430, 'x', 145, 310, (0.722, 0.722, 0.722))
add_cylinder('running_gear', 'rear_pinion_nose', 2780, 0, 430, 'x', 145, 310, (0.722, 0.722, 0.722))
add_box('chassis', 'left_hand_drive_steering_box', 535, -515, 610, 245, 175, 230, (0.722, 0.722, 0.722))
add_box('chassis', 'steering_box_left_frame_mount_plate', 500, -445, 600, 295, 28, 260, (0.176, 0.188, 0.200))
add_cylinder('running_gear', 'pitman_arm_left_hand_drive', 675, -555, 565, 'z', 62, 250, (0.722, 0.722, 0.722))
add_cylinder('running_gear', 'front_drag_link_left_hand_drive', 875, -555, 505, 'x', 34, 620, (0.722, 0.722, 0.722))
add_cylinder('running_gear', 'front_tie_rod', 735, 0, 505, 'y', 32, 1420, (0.722, 0.722, 0.722))
add_cylinder('running_gear', 'steering_damper', 905, -350, 480, 'x', 58, 520, (0.722, 0.722, 0.722))
add_box('running_gear', 'front_left_steering_knuckle_arm', 855, -690, 475, 150, 58, 60, (0.722, 0.722, 0.722))
add_box('running_gear', 'front_right_steering_knuckle_arm', 855, 690, 475, 150, 58, 60, (0.722, 0.722, 0.722))
add_cylinder('running_gear', 'front_left_brake_backing_plate', 735, -750, 395, 'y', 365, 55, (0.722, 0.722, 0.722))
add_cylinder('running_gear', 'front_right_brake_backing_plate', 735, 750, 395, 'y', 365, 55, (0.722, 0.722, 0.722))
add_box('running_gear', 'front_left_leaf_spring_layer_1', 215, -430, 305, 935, 78, 14, (0.133, 0.133, 0.133))
add_box('running_gear', 'front_left_leaf_spring_layer_2', 215, -430, 323, 820, 78, 14, (0.133, 0.133, 0.133))
add_box('running_gear', 'front_left_leaf_spring_layer_3', 215, -430, 341, 705, 78, 14, (0.133, 0.133, 0.133))
add_cylinder('running_gear', 'front_left_u_bolt_1', 670, -430, 405, 'z', 24, 210, (0.722, 0.722, 0.722))
add_cylinder('running_gear', 'front_left_u_bolt_2', 800, -430, 405, 'z', 24, 210, (0.722, 0.722, 0.722))
add_box('running_gear', 'front_right_leaf_spring_layer_1', 215, 430, 305, 935, 78, 14, (0.133, 0.133, 0.133))
add_box('running_gear', 'front_right_leaf_spring_layer_2', 215, 430, 323, 820, 78, 14, (0.133, 0.133, 0.133))
add_box('running_gear', 'front_right_leaf_spring_layer_3', 215, 430, 341, 705, 78, 14, (0.133, 0.133, 0.133))
add_cylinder('running_gear', 'front_right_u_bolt_1', 670, 430, 405, 'z', 24, 210, (0.722, 0.722, 0.722))
add_cylinder('running_gear', 'front_right_u_bolt_2', 800, 430, 405, 'z', 24, 210, (0.722, 0.722, 0.722))
add_cylinder('running_gear', 'rear_left_brake_backing_plate', 3020, -750, 395, 'y', 365, 55, (0.722, 0.722, 0.722))
add_cylinder('running_gear', 'rear_right_brake_backing_plate', 3020, 750, 395, 'y', 365, 55, (0.722, 0.722, 0.722))
add_box('running_gear', 'rear_left_leaf_spring_layer_1', 2500, -430, 305, 935, 78, 14, (0.133, 0.133, 0.133))
add_box('running_gear', 'rear_left_leaf_spring_layer_2', 2500, -430, 323, 820, 78, 14, (0.133, 0.133, 0.133))
add_box('running_gear', 'rear_left_leaf_spring_layer_3', 2500, -430, 341, 705, 78, 14, (0.133, 0.133, 0.133))
add_cylinder('running_gear', 'rear_left_u_bolt_1', 2955, -430, 405, 'z', 24, 210, (0.722, 0.722, 0.722))
add_cylinder('running_gear', 'rear_left_u_bolt_2', 3085, -430, 405, 'z', 24, 210, (0.722, 0.722, 0.722))
add_box('running_gear', 'rear_right_leaf_spring_layer_1', 2500, 430, 305, 935, 78, 14, (0.133, 0.133, 0.133))
add_box('running_gear', 'rear_right_leaf_spring_layer_2', 2500, 430, 323, 820, 78, 14, (0.133, 0.133, 0.133))
add_box('running_gear', 'rear_right_leaf_spring_layer_3', 2500, 430, 341, 705, 78, 14, (0.133, 0.133, 0.133))
add_cylinder('running_gear', 'rear_right_u_bolt_1', 2955, 430, 405, 'z', 24, 210, (0.722, 0.722, 0.722))
add_cylinder('running_gear', 'rear_right_u_bolt_2', 3085, 430, 405, 'z', 24, 210, (0.722, 0.722, 0.722))
add_cylinder('running_gear', 'front_left_outer_rim_ring', 735, -845, 395, 'y', 455, 34, (0.722, 0.722, 0.722))
add_cylinder('running_gear', 'front_left_inner_rim_shadow', 735, -855, 395, 'y', 315, 22, (0.114, 0.114, 0.114))
add_cylinder('running_gear', 'front_left_valve_stem', 865, -870, 540, 'y', 22, 50, (0.114, 0.114, 0.114))
add_cylinder('running_gear', 'front_left_lug_nut_1', 827, -877, 395, 'y', 32, 36, (0.722, 0.722, 0.722))
add_cylinder('running_gear', 'front_left_lug_nut_2', 781, -877, 474.674, 'y', 32, 36, (0.722, 0.722, 0.722))
add_cylinder('running_gear', 'front_left_lug_nut_3', 689, -877, 474.674, 'y', 32, 36, (0.722, 0.722, 0.722))
add_cylinder('running_gear', 'front_left_lug_nut_4', 643, -877, 395, 'y', 32, 36, (0.722, 0.722, 0.722))
add_cylinder('running_gear', 'front_left_lug_nut_5', 689, -877, 315.326, 'y', 32, 36, (0.722, 0.722, 0.722))
add_cylinder('running_gear', 'front_left_lug_nut_6', 781, -877, 315.326, 'y', 32, 36, (0.722, 0.722, 0.722))
add_cylinder('running_gear', 'front_right_outer_rim_ring', 735, 845, 395, 'y', 455, 34, (0.722, 0.722, 0.722))
add_cylinder('running_gear', 'front_right_inner_rim_shadow', 735, 855, 395, 'y', 315, 22, (0.114, 0.114, 0.114))
add_cylinder('running_gear', 'front_right_valve_stem', 865, 870, 540, 'y', 22, 50, (0.114, 0.114, 0.114))
add_cylinder('running_gear', 'front_right_lug_nut_1', 827, 877, 395, 'y', 32, 36, (0.722, 0.722, 0.722))
add_cylinder('running_gear', 'front_right_lug_nut_2', 781, 877, 474.674, 'y', 32, 36, (0.722, 0.722, 0.722))
add_cylinder('running_gear', 'front_right_lug_nut_3', 689, 877, 474.674, 'y', 32, 36, (0.722, 0.722, 0.722))
add_cylinder('running_gear', 'front_right_lug_nut_4', 643, 877, 395, 'y', 32, 36, (0.722, 0.722, 0.722))
add_cylinder('running_gear', 'front_right_lug_nut_5', 689, 877, 315.326, 'y', 32, 36, (0.722, 0.722, 0.722))
add_cylinder('running_gear', 'front_right_lug_nut_6', 781, 877, 315.326, 'y', 32, 36, (0.722, 0.722, 0.722))
add_cylinder('running_gear', 'rear_left_outer_rim_ring', 3020, -845, 395, 'y', 455, 34, (0.722, 0.722, 0.722))
add_cylinder('running_gear', 'rear_left_inner_rim_shadow', 3020, -855, 395, 'y', 315, 22, (0.114, 0.114, 0.114))
add_cylinder('running_gear', 'rear_left_valve_stem', 3150, -870, 540, 'y', 22, 50, (0.114, 0.114, 0.114))
add_cylinder('running_gear', 'rear_left_lug_nut_1', 3112, -877, 395, 'y', 32, 36, (0.722, 0.722, 0.722))
add_cylinder('running_gear', 'rear_left_lug_nut_2', 3066, -877, 474.674, 'y', 32, 36, (0.722, 0.722, 0.722))
add_cylinder('running_gear', 'rear_left_lug_nut_3', 2974, -877, 474.674, 'y', 32, 36, (0.722, 0.722, 0.722))
add_cylinder('running_gear', 'rear_left_lug_nut_4', 2928, -877, 395, 'y', 32, 36, (0.722, 0.722, 0.722))
add_cylinder('running_gear', 'rear_left_lug_nut_5', 2974, -877, 315.326, 'y', 32, 36, (0.722, 0.722, 0.722))
add_cylinder('running_gear', 'rear_left_lug_nut_6', 3066, -877, 315.326, 'y', 32, 36, (0.722, 0.722, 0.722))
add_cylinder('running_gear', 'rear_right_outer_rim_ring', 3020, 845, 395, 'y', 455, 34, (0.722, 0.722, 0.722))
add_cylinder('running_gear', 'rear_right_inner_rim_shadow', 3020, 855, 395, 'y', 315, 22, (0.114, 0.114, 0.114))
add_cylinder('running_gear', 'rear_right_valve_stem', 3150, 870, 540, 'y', 22, 50, (0.114, 0.114, 0.114))
add_cylinder('running_gear', 'rear_right_lug_nut_1', 3112, 877, 395, 'y', 32, 36, (0.722, 0.722, 0.722))
add_cylinder('running_gear', 'rear_right_lug_nut_2', 3066, 877, 474.674, 'y', 32, 36, (0.722, 0.722, 0.722))
add_cylinder('running_gear', 'rear_right_lug_nut_3', 2974, 877, 474.674, 'y', 32, 36, (0.722, 0.722, 0.722))
add_cylinder('running_gear', 'rear_right_lug_nut_4', 2928, 877, 395, 'y', 32, 36, (0.722, 0.722, 0.722))
add_cylinder('running_gear', 'rear_right_lug_nut_5', 2974, 877, 315.326, 'y', 32, 36, (0.722, 0.722, 0.722))
add_cylinder('running_gear', 'rear_right_lug_nut_6', 3066, 877, 315.326, 'y', 32, 36, (0.722, 0.722, 0.722))
add_cylinder('brake_system', 'front_hard_line_left_frame_run', 1180, -338, 575, 'x', 18, 1650, (0.722, 0.722, 0.722))
add_cylinder('brake_system', 'rear_hard_line_left_frame_run', 2320, -338, 575, 'x', 18, 1500, (0.722, 0.722, 0.722))
add_cylinder('brake_system', 'rear_axle_brake_line', 3020, 0, 520, 'y', 18, 1280, (0.722, 0.722, 0.722))
add_cylinder('brake_system', 'parking_brake_front_cable', 1630, -145, 545, 'x', 22, 650, (0.114, 0.114, 0.114))
add_box('brake_system', 'parking_brake_equalizer_bar', 2295, 0, 548, 175, 46, 24, (0.722, 0.722, 0.722))
add_cylinder('brake_system', 'parking_brake_equalizer_pivot_pin', 2380, 0, 548, 'y', 26, 120, (0.722, 0.722, 0.722))
add_cylinder('brake_system', 'left_rear_parking_brake_cable', 2685, -360, 535, 'x', 22, 760, (0.114, 0.114, 0.114))
add_box('brake_system', 'left_parking_brake_clevis', 3035, -520, 548, 66, 32, 34, (0.769, 0.604, 0.239))
add_cylinder('brake_system', 'left_parking_brake_return_spring', 2945, -520, 602, 'x', 34, 170, (0.133, 0.133, 0.133))
add_box('brake_system', 'left_parking_brake_cable_clip_1', 2485, -430, 545, 38, 30, 34, (0.722, 0.722, 0.722))
add_box('brake_system', 'left_parking_brake_cable_clip_2', 2805, -470, 545, 38, 30, 34, (0.722, 0.722, 0.722))
add_cylinder('brake_system', 'right_rear_parking_brake_cable', 2685, 360, 535, 'x', 22, 760, (0.114, 0.114, 0.114))
add_box('brake_system', 'right_parking_brake_clevis', 3035, 520, 548, 66, 32, 34, (0.769, 0.604, 0.239))
add_cylinder('brake_system', 'right_parking_brake_return_spring', 2945, 520, 602, 'x', 34, 170, (0.133, 0.133, 0.133))
add_box('brake_system', 'right_parking_brake_cable_clip_1', 2485, 430, 545, 38, 30, 34, (0.722, 0.722, 0.722))
add_box('brake_system', 'right_parking_brake_cable_clip_2', 2805, 470, 545, 38, 30, 34, (0.722, 0.722, 0.722))
add_box('body', 'transmission_tunnel', 1250, 0, 660, 1100, 360, 235, (0.812, 0.776, 0.667))
add_box('body', 'rear_load_floor', 2060, 0, 690, 1180, 1230, 42, (0.812, 0.776, 0.667))
add_box('body', 'rear_floor_longitudinal_rib_1', 2050, -420, 740, 1230, 38, 42, (0.812, 0.776, 0.667))
add_box('body', 'rear_floor_longitudinal_rib_2', 2050, -210, 740, 1230, 38, 42, (0.812, 0.776, 0.667))
add_box('body', 'rear_floor_longitudinal_rib_3', 2050, 0, 740, 1230, 38, 42, (0.812, 0.776, 0.667))
add_box('body', 'rear_floor_longitudinal_rib_4', 2050, 210, 740, 1230, 38, 42, (0.812, 0.776, 0.667))
add_box('body', 'rear_floor_longitudinal_rib_5', 2050, 420, 740, 1230, 38, 42, (0.812, 0.776, 0.667))
add_box('body', 'floor_cross_pressing_1', 980, 0, 735, 42, 1260, 34, (0.812, 0.776, 0.667))
add_box('body', 'floor_cross_pressing_2', 1280, 0, 735, 42, 1260, 34, (0.812, 0.776, 0.667))
add_box('body', 'floor_cross_pressing_3', 1730, 0, 735, 42, 1260, 34, (0.812, 0.776, 0.667))
add_box('body', 'floor_cross_pressing_4', 2140, 0, 735, 42, 1260, 34, (0.812, 0.776, 0.667))
add_box('body', 'floor_cross_pressing_5', 2570, 0, 735, 42, 1260, 34, (0.812, 0.776, 0.667))
add_box('body', 'floor_cross_pressing_6', 3020, 0, 735, 42, 1260, 34, (0.812, 0.776, 0.667))
add_box('body', 'left_front_wheel_arch_shadow', 365, -735, 745, 740, 34, 405, (0.114, 0.114, 0.114))
add_box('body', 'left_rear_wheel_arch_shadow', 2690, -735, 745, 690, 34, 410, (0.114, 0.114, 0.114))
add_box('body', 'left_rear_inner_wheel_tub', 2655, -505, 755, 750, 280, 385, (0.812, 0.776, 0.667))
add_box('body', 'left_tub_top_capping', 1960, -805, 1322, 1530, 105, 58, (0.812, 0.776, 0.667))
add_box('body', 'left_door_outer_skin_lower_pressing', 1235, -790, 845, 725, 34, 105, (0.812, 0.776, 0.667))
add_box('body', 'left_door_vertical_shut_gap_front', 1130, -824, 780, 18, 28, 780, (0.114, 0.114, 0.114))
add_box('body', 'left_door_vertical_shut_gap_rear', 1940, -824, 780, 18, 28, 780, (0.114, 0.114, 0.114))
add_box('body', 'left_mirror_arm', 1210, -884, 1240, 210, 26, 32, (0.722, 0.722, 0.722))
add_box('body', 'left_door_mirror_head', 1405, -930, 1195, 135, 42, 110, (0.910, 0.910, 0.910))
add_cylinder('body', 'left_fuel_or_body_plug_reference', 2935, -812, 1065, 'y', 115, 28, (0.722, 0.722, 0.722))
add_box('body', 'right_front_wheel_arch_shadow', 365, 735, 745, 740, 34, 405, (0.114, 0.114, 0.114))
add_box('body', 'right_rear_wheel_arch_shadow', 2690, 735, 745, 690, 34, 410, (0.114, 0.114, 0.114))
add_box('body', 'right_rear_inner_wheel_tub', 2655, 505, 755, 750, 280, 385, (0.812, 0.776, 0.667))
add_box('body', 'right_tub_top_capping', 1960, 805, 1322, 1530, 105, 58, (0.812, 0.776, 0.667))
add_box('body', 'right_door_outer_skin_lower_pressing', 1235, 790, 845, 725, 34, 105, (0.812, 0.776, 0.667))
add_box('body', 'right_door_vertical_shut_gap_front', 1130, 824, 780, 18, 28, 780, (0.114, 0.114, 0.114))
add_box('body', 'right_door_vertical_shut_gap_rear', 1940, 824, 780, 18, 28, 780, (0.114, 0.114, 0.114))
add_box('body', 'right_mirror_arm', 1210, 884, 1240, 210, 26, 32, (0.722, 0.722, 0.722))
add_box('body', 'right_door_mirror_head', 1405, 930, 1195, 135, 42, 110, (0.910, 0.910, 0.910))
add_cylinder('body', 'right_fuel_or_body_plug_reference', 2935, 812, 1065, 'y', 115, 28, (0.722, 0.722, 0.722))
add_cylinder('body', 'tailgate_hinge_or_chain_anchor_1', 3450, -610, 800, 'x', 54, 42, (0.722, 0.722, 0.722))
add_cylinder('body', 'tailgate_hinge_or_chain_anchor_2', 3450, -430, 1185, 'x', 54, 42, (0.722, 0.722, 0.722))
add_cylinder('body', 'tailgate_hinge_or_chain_anchor_3', 3450, 430, 1185, 'x', 54, 42, (0.722, 0.722, 0.722))
add_cylinder('body', 'tailgate_hinge_or_chain_anchor_4', 3450, 610, 800, 'x', 54, 42, (0.722, 0.722, 0.722))
add_box('body', 'tailgate_lower_pressed_panel', 3438, 0, 800, 38, 1190, 135, (0.812, 0.776, 0.667))
add_box('body', 'tailgate_upper_pressed_panel', 3438, 0, 1115, 38, 1190, 120, (0.812, 0.776, 0.667))
add_cylinder('body', 'rear_spare_tire', 3605, 0, 1020, 'x', 720, 230, (0.114, 0.114, 0.114))
add_cylinder('body', 'rear_spare_wheel_rim', 3615, 0, 1020, 'x', 385, 245, (0.722, 0.722, 0.722))
add_box('body', 'spare_wheel_carrier_vertical', 3520, 0, 800, 55, 72, 580, (0.722, 0.722, 0.722))
add_box('body', 'spare_wheel_carrier_crossbar', 3515, 0, 1015, 55, 560, 55, (0.722, 0.722, 0.722))
add_cylinder('body', 'left_rear_tail_lamp', 3470, -675, 930, 'x', 98, 38, (0.839, 0.278, 0.216))
add_cylinder('body', 'right_rear_tail_lamp', 3470, 675, 930, 'x', 98, 38, (0.839, 0.278, 0.216))
add_box('body', 'rear_license_plate', 3505, 0, 695, 24, 360, 170, (0.910, 0.910, 0.910))
add_box('front_detail', 'vertical_grille_slot_1', 82, -300, 842, 26, 42, 230, (0.114, 0.114, 0.114))
add_box('front_detail', 'vertical_grille_slot_2', 82, -200, 842, 26, 42, 230, (0.114, 0.114, 0.114))
add_box('front_detail', 'vertical_grille_slot_3', 82, -100, 842, 26, 42, 230, (0.114, 0.114, 0.114))
add_box('front_detail', 'vertical_grille_slot_4', 82, 0, 842, 26, 42, 230, (0.114, 0.114, 0.114))
add_box('front_detail', 'vertical_grille_slot_5', 82, 100, 842, 26, 42, 230, (0.114, 0.114, 0.114))
add_box('front_detail', 'vertical_grille_slot_6', 82, 200, 842, 26, 42, 230, (0.114, 0.114, 0.114))
add_box('front_detail', 'vertical_grille_slot_7', 82, 300, 842, 26, 42, 230, (0.114, 0.114, 0.114))
add_cylinder('front_detail', 'headlamp_bezel_left', 80, -495, 985, 'x', 270, 28, (0.722, 0.722, 0.722))
add_cylinder('front_detail', 'side_marker_left', 188, -683.1, 1005, 'y', 82, 26, (0.839, 0.278, 0.216))
add_cylinder('front_detail', 'headlamp_bezel_right', 80, 495, 985, 'x', 270, 28, (0.722, 0.722, 0.722))
add_cylinder('front_detail', 'side_marker_right', 188, 683.1, 1005, 'y', 82, 26, (0.839, 0.278, 0.216))
add_box('front_detail', 'front_license_plate', 5, 0, 650, 22, 360, 170, (0.910, 0.910, 0.910))
add_box('front_detail', 'front_bumper_left_end_cap', 40, -780, 525, 150, 115, 130, (0.722, 0.722, 0.722))
add_box('front_detail', 'front_bumper_right_end_cap', 40, 780, 525, 150, 115, 130, (0.722, 0.722, 0.722))
add_box('body', 'hood_center_raised_rib', 320, 0, 1277, 760, 180, 48, (0.812, 0.776, 0.667))
add_box('body', 'hood_left_outer_rib', 330, -470, 1265, 730, 52, 38, (0.812, 0.776, 0.667))
add_box('body', 'hood_right_outer_rib', 330, 470, 1265, 730, 52, 38, (0.812, 0.776, 0.667))
add_box('body', 'left_hood_latch', 810, -610, 1210, 88, 50, 58, (0.722, 0.722, 0.722))
add_box('body', 'left_cowl_vent_slot', 1020, -350, 1335, 150, 42, 26, (0.114, 0.114, 0.114))
add_box('body', 'left_windshield_outer_seal', 1122, -548, 1370, 30, 55, 470, (0.114, 0.114, 0.114))
add_box('body', 'right_hood_latch', 810, 610, 1210, 88, 50, 58, (0.722, 0.722, 0.722))
add_box('body', 'right_cowl_vent_slot', 1020, 350, 1335, 150, 42, 26, (0.114, 0.114, 0.114))
add_box('body', 'right_windshield_outer_seal', 1122, 548, 1370, 30, 55, 470, (0.114, 0.114, 0.114))
add_box('body', 'windshield_top_seal', 1122, 0, 1798, 30, 1320, 45, (0.114, 0.114, 0.114))
add_box('body', 'windshield_bottom_seal', 1122, 0, 1360, 30, 1320, 42, (0.114, 0.114, 0.114))
add_box('hard_top', 'front_hardtop_roof_rib', 1290, 0, 1810, 45, 1510, 42, (0.945, 0.933, 0.894))
add_cylinder('hard_top', 'front_left_hardtop_vertical_frame', 1290, -765, 1450, 'z', 34, 640, (0.722, 0.722, 0.722))
add_cylinder('hard_top', 'front_right_hardtop_vertical_frame', 1290, 765, 1450, 'z', 34, 640, (0.722, 0.722, 0.722))
add_box('hard_top', 'middle_hardtop_roof_rib', 1960, 0, 1810, 45, 1510, 42, (0.945, 0.933, 0.894))
add_cylinder('hard_top', 'middle_left_hardtop_vertical_frame', 1960, -765, 1450, 'z', 34, 640, (0.722, 0.722, 0.722))
add_cylinder('hard_top', 'middle_right_hardtop_vertical_frame', 1960, 765, 1450, 'z', 34, 640, (0.722, 0.722, 0.722))
add_box('hard_top', 'rear_hardtop_roof_rib', 2640, 0, 1810, 45, 1510, 42, (0.945, 0.933, 0.894))
add_cylinder('hard_top', 'rear_left_hardtop_vertical_frame', 2640, -765, 1450, 'z', 34, 640, (0.722, 0.722, 0.722))
add_cylinder('hard_top', 'rear_right_hardtop_vertical_frame', 2640, 765, 1450, 'z', 34, 640, (0.722, 0.722, 0.722))
add_box('hard_top', 'tail_hardtop_roof_rib', 3300, 0, 1810, 45, 1510, 42, (0.945, 0.933, 0.894))
add_cylinder('hard_top', 'tail_left_hardtop_vertical_frame', 3300, -765, 1450, 'z', 34, 640, (0.722, 0.722, 0.722))
add_cylinder('hard_top', 'tail_right_hardtop_vertical_frame', 3300, 765, 1450, 'z', 34, 640, (0.722, 0.722, 0.722))
add_box('hard_top', 'left_hardtop_lower_retainer_rail', 1240, -830, 1288, 2200, 42, 46, (0.722, 0.722, 0.722))
add_box('hard_top', 'left_front_window_rubber_seal', 1420, -842, 1435, 535, 28, 355, (0.114, 0.114, 0.114))
add_box('hard_top', 'left_rear_window_rubber_seal', 2190, -842, 1435, 650, 28, 355, (0.114, 0.114, 0.114))
add_box('hard_top', 'left_hardtop_vertical_joint_1', 1320, -826, 1320, 22, 28, 570, (0.114, 0.114, 0.114))
add_box('hard_top', 'left_hardtop_vertical_joint_2', 1820, -826, 1320, 22, 28, 570, (0.114, 0.114, 0.114))
add_box('hard_top', 'left_hardtop_vertical_joint_3', 2500, -826, 1320, 22, 28, 570, (0.114, 0.114, 0.114))
add_box('hard_top', 'left_hardtop_vertical_joint_4', 3180, -826, 1320, 22, 28, 570, (0.114, 0.114, 0.114))
add_box('body', 'left_side_step_board', 1540, -865, 620, 1120, 210, 55, (0.945, 0.933, 0.894))
add_box('body', 'left_diesel_badge', 2925, -822, 980, 120, 24, 42, (0.722, 0.722, 0.722))
add_box('hard_top', 'right_hardtop_lower_retainer_rail', 1240, 830, 1288, 2200, 42, 46, (0.722, 0.722, 0.722))
add_box('hard_top', 'right_front_window_rubber_seal', 1420, 842, 1435, 535, 28, 355, (0.114, 0.114, 0.114))
add_box('hard_top', 'right_rear_window_rubber_seal', 2190, 842, 1435, 650, 28, 355, (0.114, 0.114, 0.114))
add_box('hard_top', 'right_hardtop_vertical_joint_1', 1320, 826, 1320, 22, 28, 570, (0.114, 0.114, 0.114))
add_box('hard_top', 'right_hardtop_vertical_joint_2', 1820, 826, 1320, 22, 28, 570, (0.114, 0.114, 0.114))
add_box('hard_top', 'right_hardtop_vertical_joint_3', 2500, 826, 1320, 22, 28, 570, (0.114, 0.114, 0.114))
add_box('hard_top', 'right_hardtop_vertical_joint_4', 3180, 826, 1320, 22, 28, 570, (0.114, 0.114, 0.114))
add_box('body', 'right_side_step_board', 1540, 865, 620, 1120, 210, 55, (0.945, 0.933, 0.894))
add_box('body', 'right_diesel_badge', 2925, 822, 980, 120, 24, 42, (0.722, 0.722, 0.722))
add_box('hard_top', 'rear_window_rubber_seal', 3470, 0, 1460, 28, 850, 330, (0.114, 0.114, 0.114))
add_box('hard_top', 'rear_hardtop_window', 3485, 0, 1470, 18, 780, 275, (0.435, 0.647, 0.722))
add_box('hard_top', 'rear_corner_glass_or_seal_45', 3500, -555, 1415, 28, 170, 300, (0.435, 0.647, 0.722))
add_box('hard_top', 'rear_corner_glass_or_seal_325', 3500, -275, 1415, 28, 170, 300, (0.435, 0.647, 0.722))
add_box('hard_top', 'rear_corner_glass_or_seal_875', 3500, 275, 1415, 28, 170, 300, (0.435, 0.647, 0.722))
add_box('hard_top', 'rear_corner_glass_or_seal_1155', 3500, 555, 1415, 28, 170, 300, (0.435, 0.647, 0.722))
add_box('front_detail', 'front_grille_black_mesh_horizontal_texture_1', 64, 0, 860, 18, 560, 12, (0.149, 0.220, 0.247))
add_box('front_detail', 'front_grille_black_mesh_horizontal_texture_2', 64, 0, 895, 18, 560, 12, (0.149, 0.220, 0.247))
add_box('front_detail', 'front_grille_black_mesh_horizontal_texture_3', 64, 0, 930, 18, 560, 12, (0.149, 0.220, 0.247))
add_box('front_detail', 'front_grille_black_mesh_horizontal_texture_4', 64, 0, 965, 18, 560, 12, (0.149, 0.220, 0.247))
add_box('front_detail', 'front_grille_black_mesh_vertical_texture_1', 62, -260, 852, 20, 12, 145, (0.149, 0.220, 0.247))
add_box('front_detail', 'front_grille_black_mesh_vertical_texture_2', 62, -170, 852, 20, 12, 145, (0.149, 0.220, 0.247))
add_box('front_detail', 'front_grille_black_mesh_vertical_texture_3', 62, -80, 852, 20, 12, 145, (0.149, 0.220, 0.247))
add_box('front_detail', 'front_grille_black_mesh_vertical_texture_4', 62, 80, 852, 20, 12, 145, (0.149, 0.220, 0.247))
add_box('front_detail', 'front_grille_black_mesh_vertical_texture_5', 62, 170, 852, 20, 12, 145, (0.149, 0.220, 0.247))
add_box('front_detail', 'front_grille_black_mesh_vertical_texture_6', 62, 260, 852, 20, 12, 145, (0.149, 0.220, 0.247))
add_cylinder('front_detail', 'grille_surround_screw_1', 58, -325, 812, 'x', 28, 20, (0.851, 0.835, 0.784))
add_cylinder('front_detail', 'grille_surround_screw_2', 58, -230, 1008, 'x', 28, 20, (0.851, 0.835, 0.784))
add_cylinder('front_detail', 'grille_surround_screw_3', 58, 230, 1008, 'x', 28, 20, (0.851, 0.835, 0.784))
add_cylinder('front_detail', 'grille_surround_screw_4', 58, 325, 812, 'x', 28, 20, (0.851, 0.835, 0.784))
add_box('front_detail', 'toyota_grille_letter_t_top', 52, -190, 940, 16, 58, 12, (0.839, 0.749, 0.278))
add_box('front_detail', 'toyota_grille_letter_t_stem', 52, -190, 895, 16, 13, 54, (0.839, 0.749, 0.278))
add_box('front_detail', 'toyota_grille_letter_o1_top', 52, -98, 938, 16, 52, 12, (0.839, 0.749, 0.278))
add_box('front_detail', 'toyota_grille_letter_o1_bottom', 52, -98, 893, 16, 52, 12, (0.839, 0.749, 0.278))
add_box('front_detail', 'toyota_grille_letter_o1_left', 52, -121, 900, 16, 11, 42, (0.839, 0.749, 0.278))
add_box('front_detail', 'toyota_grille_letter_o1_right', 52, -75, 900, 16, 11, 42, (0.839, 0.749, 0.278))
add_box('front_detail', 'toyota_grille_letter_o2_top', 52, 98, 938, 16, 52, 12, (0.839, 0.749, 0.278))
add_box('front_detail', 'toyota_grille_letter_o2_bottom', 52, 98, 893, 16, 52, 12, (0.839, 0.749, 0.278))
add_box('front_detail', 'toyota_grille_letter_o2_left', 52, 75, 900, 16, 11, 42, (0.839, 0.749, 0.278))
add_box('front_detail', 'toyota_grille_letter_o2_right', 52, 121, 900, 16, 11, 42, (0.839, 0.749, 0.278))
add_box('front_detail', 'toyota_grille_letter_y_left_upper', 52, -21, 928, 16, 18, 12, (0.839, 0.749, 0.278))
add_box('front_detail', 'toyota_grille_letter_y_right_upper', 52, 21, 928, 16, 18, 12, (0.839, 0.749, 0.278))
add_box('front_detail', 'toyota_grille_letter_y_stem', 52, 0, 895, 16, 12, 42, (0.839, 0.749, 0.278))
add_box('front_detail', 'toyota_grille_letter_a_left', 52, 184, 895, 16, 11, 55, (0.839, 0.749, 0.278))
add_box('front_detail', 'toyota_grille_letter_a_right', 52, 228, 895, 16, 11, 55, (0.839, 0.749, 0.278))
add_box('front_detail', 'toyota_grille_letter_a_top', 52, 206, 938, 16, 52, 12, (0.839, 0.749, 0.278))
add_box('front_detail', 'toyota_grille_letter_a_bar', 52, 206, 915, 16, 42, 10, (0.839, 0.749, 0.278))
add_box('front_detail', 'left_front_fender_turn_signal_base', 290, -642, 1058, 155, 80, 24, (0.851, 0.835, 0.784))
add_cylinder('front_detail', 'left_front_fender_turn_signal_lens', 298, -642, 1075, 'z', 78, 32, (0.851, 0.471, 0.141))
add_cylinder('front_detail', 'left_headlamp_glass_highlight', 64, -445, 1035, 'x', 126, 18, (0.894, 0.863, 0.780))
add_cylinder('front_detail', 'left_headlamp_mount_screw_upper', 58, -375, 1094, 'x', 22, 18, (0.851, 0.835, 0.784))
add_cylinder('front_detail', 'left_headlamp_mount_screw_lower', 58, -515, 876, 'x', 22, 18, (0.851, 0.835, 0.784))
add_box('body', 'left_front_quarter_louver_slot_1', 885, -826, 890, 175, 24, 14, (0.149, 0.220, 0.247))
add_box('body', 'left_front_quarter_louver_highlight_1', 880, -812, 906, 160, 16, 8, (0.894, 0.863, 0.780))
add_box('body', 'left_front_quarter_louver_slot_2', 885, -826, 925, 175, 24, 14, (0.149, 0.220, 0.247))
add_box('body', 'left_front_quarter_louver_highlight_2', 880, -812, 941, 160, 16, 8, (0.894, 0.863, 0.780))
add_box('body', 'left_front_quarter_louver_slot_3', 885, -826, 960, 175, 24, 14, (0.149, 0.220, 0.247))
add_box('body', 'left_front_quarter_louver_highlight_3', 880, -812, 976, 160, 16, 8, (0.894, 0.863, 0.780))
add_box('body', 'left_front_quarter_louver_slot_4', 885, -826, 995, 175, 24, 14, (0.149, 0.220, 0.247))
add_box('body', 'left_front_quarter_louver_highlight_4', 880, -812, 1011, 160, 16, 8, (0.894, 0.863, 0.780))
add_box('body', 'left_front_quarter_louver_slot_5', 885, -826, 1030, 175, 24, 14, (0.149, 0.220, 0.247))
add_box('body', 'left_front_quarter_louver_highlight_5', 880, -812, 1046, 160, 16, 8, (0.894, 0.863, 0.780))
add_box('body', 'left_beltline_trim_front_door', 1140, -834, 1118, 780, 22, 28, (0.851, 0.835, 0.784))
add_box('body', 'left_beltline_trim_rear_tub', 1965, -834, 1118, 1390, 22, 28, (0.851, 0.835, 0.784))
add_box('body', 'left_door_outer_skin_upper_pressing', 1235, -789, 1040, 725, 34, 70, (0.616, 0.588, 0.494))
add_box('body', 'left_door_skin_lower_recess_shadow', 1235, -789, 885, 725, 32, 76, (0.616, 0.588, 0.494))
add_box('body', 'left_door_window_front_vertical_frame', 1115, -812, 1192, 34, 35, 385, (0.067, 0.075, 0.082))
add_box('body', 'left_door_window_rear_vertical_frame', 1642, -812, 1192, 34, 35, 385, (0.067, 0.075, 0.082))
add_box('body', 'left_door_window_top_frame', 1115, -812, 1546, 560, 35, 34, (0.067, 0.075, 0.082))
add_box('body', 'left_door_window_bottom_frame', 1115, -812, 1186, 560, 35, 30, (0.067, 0.075, 0.082))
add_cylinder('body', 'left_door_lock_cylinder', 1645, -835, 1032, 'y', 36, 22, (0.851, 0.835, 0.784))
add_cylinder('body', 'left_door_hinge_pin_cap_1', 1126, -843, 820, 'y', 32, 26, (0.851, 0.835, 0.784))
add_cylinder('body', 'left_door_hinge_pin_cap_2', 1126, -843, 930, 'y', 32, 26, (0.851, 0.835, 0.784))
add_cylinder('body', 'left_door_hinge_pin_cap_3', 1126, -843, 1180, 'y', 32, 26, (0.851, 0.835, 0.784))
add_cylinder('body', 'left_door_hinge_pin_cap_4', 1126, -843, 1290, 'y', 32, 26, (0.851, 0.835, 0.784))
add_box('hard_top', 'left_hardtop_front_window_upper_inner_shadow', 1420, -854, 1732, 500, 18, 22, (0.149, 0.220, 0.247))
add_box('hard_top', 'left_hardtop_front_window_lower_inner_shadow', 1420, -854, 1360, 500, 18, 22, (0.149, 0.220, 0.247))
add_box('hard_top', 'left_hardtop_front_window_sliding_mullion', 1510, -858, 1438, 28, 24, 300, (0.067, 0.075, 0.082))
add_cylinder('hard_top', 'left_hardtop_front_window_rounded_corner_1', 1170, -862, 1360, 'y', 54, 24, (0.114, 0.114, 0.114))
add_cylinder('hard_top', 'left_hardtop_front_window_rounded_corner_2', 1670, -862, 1360, 'y', 54, 24, (0.114, 0.114, 0.114))
add_cylinder('hard_top', 'left_hardtop_front_window_rounded_corner_3', 1170, -862, 1680, 'y', 54, 24, (0.114, 0.114, 0.114))
add_cylinder('hard_top', 'left_hardtop_front_window_rounded_corner_4', 1670, -862, 1680, 'y', 54, 24, (0.114, 0.114, 0.114))
add_box('hard_top', 'left_hardtop_rear_window_upper_inner_shadow', 2190, -854, 1732, 610, 18, 22, (0.149, 0.220, 0.247))
add_box('hard_top', 'left_hardtop_rear_window_lower_inner_shadow', 2190, -854, 1360, 610, 18, 22, (0.149, 0.220, 0.247))
add_box('hard_top', 'left_hardtop_rear_window_sliding_mullion', 2299.8, -858, 1438, 28, 24, 300, (0.067, 0.075, 0.082))
add_cylinder('hard_top', 'left_hardtop_rear_window_rounded_corner_1', 1885, -862, 1360, 'y', 54, 24, (0.114, 0.114, 0.114))
add_cylinder('hard_top', 'left_hardtop_rear_window_rounded_corner_2', 2495, -862, 1360, 'y', 54, 24, (0.114, 0.114, 0.114))
add_cylinder('hard_top', 'left_hardtop_rear_window_rounded_corner_3', 1885, -862, 1680, 'y', 54, 24, (0.114, 0.114, 0.114))
add_cylinder('hard_top', 'left_hardtop_rear_window_rounded_corner_4', 2495, -862, 1680, 'y', 54, 24, (0.114, 0.114, 0.114))
add_box('hard_top', 'left_roof_drip_rail_outer_shadow', 1235, -862, 1784, 2275, 28, 30, (0.616, 0.588, 0.494))
add_box('hard_top', 'left_roof_side_panel_subtle_vertical_pressing_1', 1420, -804, 1325, 20, 18, 520, (0.616, 0.588, 0.494))
add_box('hard_top', 'left_roof_side_panel_subtle_vertical_pressing_2', 1840, -804, 1325, 20, 18, 520, (0.616, 0.588, 0.494))
add_box('hard_top', 'left_roof_side_panel_subtle_vertical_pressing_3', 2260, -804, 1325, 20, 18, 520, (0.616, 0.588, 0.494))
add_box('hard_top', 'left_roof_side_panel_subtle_vertical_pressing_4', 2680, -804, 1325, 20, 18, 520, (0.616, 0.588, 0.494))
add_box('hard_top', 'left_roof_side_panel_subtle_vertical_pressing_5', 3100, -804, 1325, 20, 18, 520, (0.616, 0.588, 0.494))
add_box('body', 'left_front_black_fender_flare_arc_1', 1046.32, -823, 548.746, 68, 46, 34, (0.067, 0.075, 0.082))
add_box('body', 'left_front_black_fender_flare_arc_2', 998.868, -823, 627.72, 68, 46, 34, (0.067, 0.075, 0.082))
add_box('body', 'left_front_black_fender_flare_arc_3', 933.72, -823, 692.868, 68, 46, 34, (0.067, 0.075, 0.082))
add_box('body', 'left_front_black_fender_flare_arc_4', 854.746, -823, 740.32, 68, 46, 34, (0.067, 0.075, 0.082))
add_box('body', 'left_front_black_fender_flare_arc_5', 766.639, -823, 767.257, 68, 46, 34, (0.067, 0.075, 0.082))
add_box('body', 'left_front_black_fender_flare_arc_6', 674.632, -823, 772.079, 68, 46, 34, (0.067, 0.075, 0.082))
add_box('body', 'left_front_black_fender_flare_arc_7', 584.192, -823, 754.499, 68, 46, 34, (0.067, 0.075, 0.082))
add_box('body', 'left_front_black_fender_flare_arc_8', 500.691, -823, 715.562, 68, 46, 34, (0.067, 0.075, 0.082))
add_box('body', 'left_front_black_fender_flare_arc_9', 429.09, -823, 657.581, 68, 46, 34, (0.067, 0.075, 0.082))
add_box('body', 'left_front_black_fender_flare_arc_10', 373.642, -823, 584, 68, 46, 34, (0.067, 0.075, 0.082))
add_box('body', 'left_rear_black_fender_flare_arc_1', 3319.44, -823, 543.459, 68, 46, 34, (0.067, 0.075, 0.082))
add_box('body', 'left_rear_black_fender_flare_arc_2', 3273.62, -823, 619.716, 68, 46, 34, (0.067, 0.075, 0.082))
add_box('body', 'left_rear_black_fender_flare_arc_3', 3210.72, -823, 682.624, 68, 46, 34, (0.067, 0.075, 0.082))
add_box('body', 'left_rear_black_fender_flare_arc_4', 3134.46, -823, 728.444, 68, 46, 34, (0.067, 0.075, 0.082))
add_box('body', 'left_rear_black_fender_flare_arc_5', 3049.38, -823, 754.455, 68, 46, 34, (0.067, 0.075, 0.082))
add_box('body', 'left_rear_black_fender_flare_arc_6', 2960.54, -823, 759.111, 68, 46, 34, (0.067, 0.075, 0.082))
add_box('body', 'left_rear_black_fender_flare_arc_7', 2873.21, -823, 742.136, 68, 46, 34, (0.067, 0.075, 0.082))
add_box('body', 'left_rear_black_fender_flare_arc_8', 2792.58, -823, 704.538, 68, 46, 34, (0.067, 0.075, 0.082))
add_box('body', 'left_rear_black_fender_flare_arc_9', 2723.44, -823, 648.55, 68, 46, 34, (0.067, 0.075, 0.082))
add_box('body', 'left_rear_black_fender_flare_arc_10', 2669.9, -823, 577.5, 68, 46, 34, (0.067, 0.075, 0.082))
add_box('body', 'left_side_step_tread_strip_1', 1120, -872, 674, 130, 162, 12, (0.851, 0.835, 0.784))
add_box('body', 'left_side_step_tread_strip_2', 1320, -872, 674, 130, 162, 12, (0.851, 0.835, 0.784))
add_box('body', 'left_side_step_tread_strip_3', 1520, -872, 674, 130, 162, 12, (0.851, 0.835, 0.784))
add_box('body', 'left_side_step_tread_strip_4', 1720, -872, 674, 130, 162, 12, (0.851, 0.835, 0.784))
add_box('body', 'left_side_step_tread_strip_5', 1920, -872, 674, 130, 162, 12, (0.851, 0.835, 0.784))
add_box('body', 'left_side_step_drop_bracket_1', 1180, -760, 530, 52, 38, 155, (0.176, 0.188, 0.200))
add_box('body', 'left_side_step_drop_bracket_2', 1540, -760, 530, 52, 38, 155, (0.176, 0.188, 0.200))
add_box('body', 'left_side_step_drop_bracket_3', 1900, -760, 530, 52, 38, 155, (0.176, 0.188, 0.200))
add_box('body', 'left_front_mud_flap', 420, -780, 190, 42, 135, 280, (0.114, 0.114, 0.114))
add_box('body', 'left_rear_mud_flap', 3350, -780, 185, 42, 135, 300, (0.114, 0.114, 0.114))
add_box('front_detail', 'right_front_fender_turn_signal_base', 290, 642, 1058, 155, 80, 24, (0.851, 0.835, 0.784))
add_cylinder('front_detail', 'right_front_fender_turn_signal_lens', 298, 642, 1075, 'z', 78, 32, (0.851, 0.471, 0.141))
add_cylinder('front_detail', 'right_headlamp_glass_highlight', 64, 445, 1035, 'x', 126, 18, (0.894, 0.863, 0.780))
add_cylinder('front_detail', 'right_headlamp_mount_screw_upper', 58, 375, 1094, 'x', 22, 18, (0.851, 0.835, 0.784))
add_cylinder('front_detail', 'right_headlamp_mount_screw_lower', 58, 515, 876, 'x', 22, 18, (0.851, 0.835, 0.784))
add_box('body', 'right_front_quarter_louver_slot_1', 885, 826, 890, 175, 24, 14, (0.149, 0.220, 0.247))
add_box('body', 'right_front_quarter_louver_highlight_1', 880, 812, 906, 160, 16, 8, (0.894, 0.863, 0.780))
add_box('body', 'right_front_quarter_louver_slot_2', 885, 826, 925, 175, 24, 14, (0.149, 0.220, 0.247))
add_box('body', 'right_front_quarter_louver_highlight_2', 880, 812, 941, 160, 16, 8, (0.894, 0.863, 0.780))
add_box('body', 'right_front_quarter_louver_slot_3', 885, 826, 960, 175, 24, 14, (0.149, 0.220, 0.247))
add_box('body', 'right_front_quarter_louver_highlight_3', 880, 812, 976, 160, 16, 8, (0.894, 0.863, 0.780))
add_box('body', 'right_front_quarter_louver_slot_4', 885, 826, 995, 175, 24, 14, (0.149, 0.220, 0.247))
add_box('body', 'right_front_quarter_louver_highlight_4', 880, 812, 1011, 160, 16, 8, (0.894, 0.863, 0.780))
add_box('body', 'right_front_quarter_louver_slot_5', 885, 826, 1030, 175, 24, 14, (0.149, 0.220, 0.247))
add_box('body', 'right_front_quarter_louver_highlight_5', 880, 812, 1046, 160, 16, 8, (0.894, 0.863, 0.780))
add_box('body', 'right_beltline_trim_front_door', 1140, 834, 1118, 780, 22, 28, (0.851, 0.835, 0.784))
add_box('body', 'right_beltline_trim_rear_tub', 1965, 834, 1118, 1390, 22, 28, (0.851, 0.835, 0.784))
add_box('body', 'right_door_outer_skin_upper_pressing', 1235, 789, 1040, 725, 34, 70, (0.616, 0.588, 0.494))
add_box('body', 'right_door_skin_lower_recess_shadow', 1235, 789, 885, 725, 32, 76, (0.616, 0.588, 0.494))
add_box('body', 'right_door_window_front_vertical_frame', 1115, 812, 1192, 34, 35, 385, (0.067, 0.075, 0.082))
add_box('body', 'right_door_window_rear_vertical_frame', 1642, 812, 1192, 34, 35, 385, (0.067, 0.075, 0.082))
add_box('body', 'right_door_window_top_frame', 1115, 812, 1546, 560, 35, 34, (0.067, 0.075, 0.082))
add_box('body', 'right_door_window_bottom_frame', 1115, 812, 1186, 560, 35, 30, (0.067, 0.075, 0.082))
add_cylinder('body', 'right_door_lock_cylinder', 1645, 835, 1032, 'y', 36, 22, (0.851, 0.835, 0.784))
add_cylinder('body', 'right_door_hinge_pin_cap_1', 1126, 843, 820, 'y', 32, 26, (0.851, 0.835, 0.784))
add_cylinder('body', 'right_door_hinge_pin_cap_2', 1126, 843, 930, 'y', 32, 26, (0.851, 0.835, 0.784))
add_cylinder('body', 'right_door_hinge_pin_cap_3', 1126, 843, 1180, 'y', 32, 26, (0.851, 0.835, 0.784))
add_cylinder('body', 'right_door_hinge_pin_cap_4', 1126, 843, 1290, 'y', 32, 26, (0.851, 0.835, 0.784))
add_box('hard_top', 'right_hardtop_front_window_upper_inner_shadow', 1420, 854, 1732, 500, 18, 22, (0.149, 0.220, 0.247))
add_box('hard_top', 'right_hardtop_front_window_lower_inner_shadow', 1420, 854, 1360, 500, 18, 22, (0.149, 0.220, 0.247))
add_box('hard_top', 'right_hardtop_front_window_sliding_mullion', 1510, 858, 1438, 28, 24, 300, (0.067, 0.075, 0.082))
add_cylinder('hard_top', 'right_hardtop_front_window_rounded_corner_1', 1170, 862, 1360, 'y', 54, 24, (0.114, 0.114, 0.114))
add_cylinder('hard_top', 'right_hardtop_front_window_rounded_corner_2', 1670, 862, 1360, 'y', 54, 24, (0.114, 0.114, 0.114))
add_cylinder('hard_top', 'right_hardtop_front_window_rounded_corner_3', 1170, 862, 1680, 'y', 54, 24, (0.114, 0.114, 0.114))
add_cylinder('hard_top', 'right_hardtop_front_window_rounded_corner_4', 1670, 862, 1680, 'y', 54, 24, (0.114, 0.114, 0.114))
add_box('hard_top', 'right_hardtop_rear_window_upper_inner_shadow', 2190, 854, 1732, 610, 18, 22, (0.149, 0.220, 0.247))
add_box('hard_top', 'right_hardtop_rear_window_lower_inner_shadow', 2190, 854, 1360, 610, 18, 22, (0.149, 0.220, 0.247))
add_box('hard_top', 'right_hardtop_rear_window_sliding_mullion', 2299.8, 858, 1438, 28, 24, 300, (0.067, 0.075, 0.082))
add_cylinder('hard_top', 'right_hardtop_rear_window_rounded_corner_1', 1885, 862, 1360, 'y', 54, 24, (0.114, 0.114, 0.114))
add_cylinder('hard_top', 'right_hardtop_rear_window_rounded_corner_2', 2495, 862, 1360, 'y', 54, 24, (0.114, 0.114, 0.114))
add_cylinder('hard_top', 'right_hardtop_rear_window_rounded_corner_3', 1885, 862, 1680, 'y', 54, 24, (0.114, 0.114, 0.114))
add_cylinder('hard_top', 'right_hardtop_rear_window_rounded_corner_4', 2495, 862, 1680, 'y', 54, 24, (0.114, 0.114, 0.114))
add_box('hard_top', 'right_roof_drip_rail_outer_shadow', 1235, 862, 1784, 2275, 28, 30, (0.616, 0.588, 0.494))
add_box('hard_top', 'right_roof_side_panel_subtle_vertical_pressing_1', 1420, 804, 1325, 20, 18, 520, (0.616, 0.588, 0.494))
add_box('hard_top', 'right_roof_side_panel_subtle_vertical_pressing_2', 1840, 804, 1325, 20, 18, 520, (0.616, 0.588, 0.494))
add_box('hard_top', 'right_roof_side_panel_subtle_vertical_pressing_3', 2260, 804, 1325, 20, 18, 520, (0.616, 0.588, 0.494))
add_box('hard_top', 'right_roof_side_panel_subtle_vertical_pressing_4', 2680, 804, 1325, 20, 18, 520, (0.616, 0.588, 0.494))
add_box('hard_top', 'right_roof_side_panel_subtle_vertical_pressing_5', 3100, 804, 1325, 20, 18, 520, (0.616, 0.588, 0.494))
add_box('body', 'right_front_black_fender_flare_arc_1', 1046.32, 823, 548.746, 68, 46, 34, (0.067, 0.075, 0.082))
add_box('body', 'right_front_black_fender_flare_arc_2', 998.868, 823, 627.72, 68, 46, 34, (0.067, 0.075, 0.082))
add_box('body', 'right_front_black_fender_flare_arc_3', 933.72, 823, 692.868, 68, 46, 34, (0.067, 0.075, 0.082))
add_box('body', 'right_front_black_fender_flare_arc_4', 854.746, 823, 740.32, 68, 46, 34, (0.067, 0.075, 0.082))
add_box('body', 'right_front_black_fender_flare_arc_5', 766.639, 823, 767.257, 68, 46, 34, (0.067, 0.075, 0.082))
add_box('body', 'right_front_black_fender_flare_arc_6', 674.632, 823, 772.079, 68, 46, 34, (0.067, 0.075, 0.082))
add_box('body', 'right_front_black_fender_flare_arc_7', 584.192, 823, 754.499, 68, 46, 34, (0.067, 0.075, 0.082))
add_box('body', 'right_front_black_fender_flare_arc_8', 500.691, 823, 715.562, 68, 46, 34, (0.067, 0.075, 0.082))
add_box('body', 'right_front_black_fender_flare_arc_9', 429.09, 823, 657.581, 68, 46, 34, (0.067, 0.075, 0.082))
add_box('body', 'right_front_black_fender_flare_arc_10', 373.642, 823, 584, 68, 46, 34, (0.067, 0.075, 0.082))
add_box('body', 'right_rear_black_fender_flare_arc_1', 3319.44, 823, 543.459, 68, 46, 34, (0.067, 0.075, 0.082))
add_box('body', 'right_rear_black_fender_flare_arc_2', 3273.62, 823, 619.716, 68, 46, 34, (0.067, 0.075, 0.082))
add_box('body', 'right_rear_black_fender_flare_arc_3', 3210.72, 823, 682.624, 68, 46, 34, (0.067, 0.075, 0.082))
add_box('body', 'right_rear_black_fender_flare_arc_4', 3134.46, 823, 728.444, 68, 46, 34, (0.067, 0.075, 0.082))
add_box('body', 'right_rear_black_fender_flare_arc_5', 3049.38, 823, 754.455, 68, 46, 34, (0.067, 0.075, 0.082))
add_box('body', 'right_rear_black_fender_flare_arc_6', 2960.54, 823, 759.111, 68, 46, 34, (0.067, 0.075, 0.082))
add_box('body', 'right_rear_black_fender_flare_arc_7', 2873.21, 823, 742.136, 68, 46, 34, (0.067, 0.075, 0.082))
add_box('body', 'right_rear_black_fender_flare_arc_8', 2792.58, 823, 704.538, 68, 46, 34, (0.067, 0.075, 0.082))
add_box('body', 'right_rear_black_fender_flare_arc_9', 2723.44, 823, 648.55, 68, 46, 34, (0.067, 0.075, 0.082))
add_box('body', 'right_rear_black_fender_flare_arc_10', 2669.9, 823, 577.5, 68, 46, 34, (0.067, 0.075, 0.082))
add_box('body', 'right_side_step_tread_strip_1', 1120, 872, 674, 130, 162, 12, (0.851, 0.835, 0.784))
add_box('body', 'right_side_step_tread_strip_2', 1320, 872, 674, 130, 162, 12, (0.851, 0.835, 0.784))
add_box('body', 'right_side_step_tread_strip_3', 1520, 872, 674, 130, 162, 12, (0.851, 0.835, 0.784))
add_box('body', 'right_side_step_tread_strip_4', 1720, 872, 674, 130, 162, 12, (0.851, 0.835, 0.784))
add_box('body', 'right_side_step_tread_strip_5', 1920, 872, 674, 130, 162, 12, (0.851, 0.835, 0.784))
add_box('body', 'right_side_step_drop_bracket_1', 1180, 760, 530, 52, 38, 155, (0.176, 0.188, 0.200))
add_box('body', 'right_side_step_drop_bracket_2', 1540, 760, 530, 52, 38, 155, (0.176, 0.188, 0.200))
add_box('body', 'right_side_step_drop_bracket_3', 1900, 760, 530, 52, 38, 155, (0.176, 0.188, 0.200))
add_box('body', 'right_front_mud_flap', 420, 780, 190, 42, 135, 280, (0.114, 0.114, 0.114))
add_box('body', 'right_rear_mud_flap', 3350, 780, 185, 42, 135, 300, (0.114, 0.114, 0.114))
add_box('hard_top', 'rear_split_door_center_seal', 3505, 0, 1180, 30, 36, 650, (0.114, 0.114, 0.114))
add_box('hard_top', 'rear_door_left_glass_dark_inset', 3502, -250, 1470, 24, 340, 252, (0.149, 0.220, 0.247))
add_box('hard_top', 'rear_door_right_glass_dark_inset', 3502, 250, 1470, 24, 340, 252, (0.149, 0.220, 0.247))
add_box('hard_top', 'rear_door_window_center_mullion', 3496, 0, 1462, 34, 34, 304, (0.067, 0.075, 0.082))
add_cylinder('hard_top', 'rear_left_door_hinge_barrel_1', 3520, -650, 1180, 'z', 42, 165, (0.851, 0.835, 0.784))
add_cylinder('hard_top', 'rear_left_door_hinge_barrel_2', 3520, -650, 1510, 'z', 42, 165, (0.851, 0.835, 0.784))
add_box('hard_top', 'rear_left_door_pull_handle', 3526, -110, 1205, 28, 120, 44, (0.851, 0.835, 0.784))
add_cylinder('hard_top', 'rear_left_door_lock_button', 3536, -190, 1190, 'x', 38, 22, (0.851, 0.835, 0.784))
add_cylinder('hard_top', 'rear_right_door_hinge_barrel_1', 3520, 650, 1180, 'z', 42, 165, (0.851, 0.835, 0.784))
add_cylinder('hard_top', 'rear_right_door_hinge_barrel_2', 3520, 650, 1510, 'z', 42, 165, (0.851, 0.835, 0.784))
add_box('hard_top', 'rear_right_door_pull_handle', 3526, 110, 1205, 28, 120, 44, (0.851, 0.835, 0.784))
add_cylinder('hard_top', 'rear_right_door_lock_button', 3536, 190, 1190, 'x', 38, 22, (0.851, 0.835, 0.784))
add_cylinder('body', 'rear_spare_sidewall_highlight_ring', 3628, 0, 1020, 'x', 585, 18, (0.616, 0.588, 0.494))
add_box('body', 'rear_spare_wheel_spoke_1', 3650, 142, 1008, 28, 205, 24, (0.851, 0.835, 0.784))
add_box('body', 'rear_spare_wheel_spoke_2', 3650, 71, 1130.98, 28, 205, 24, (0.851, 0.835, 0.784))
add_box('body', 'rear_spare_wheel_spoke_3', 3650, -71, 1130.98, 28, 205, 24, (0.851, 0.835, 0.784))
add_box('body', 'rear_spare_wheel_spoke_4', 3650, -142, 1008, 28, 205, 24, (0.851, 0.835, 0.784))
add_box('body', 'rear_spare_wheel_spoke_5', 3650, -71, 885.024, 28, 205, 24, (0.851, 0.835, 0.784))
add_box('body', 'rear_spare_wheel_spoke_6', 3650, 71, 885.024, 28, 205, 24, (0.851, 0.835, 0.784))
add_box('body', 'windshield_center_divider_bar', 1116, 0, 1570, 30, 42, 420, (0.067, 0.075, 0.082))
add_box('body', 'windshield_upper_inner_glare_band', 1112, 0, 1588, 20, 1210, 28, (0.149, 0.220, 0.247))
add_box('body', 'windshield_lower_inner_glare_band', 1112, 0, 1420, 20, 1185, 24, (0.149, 0.220, 0.247))
add_box('body', 'hood_front_lip_shadow', 42, 0, 1222, 36, 1320, 34, (0.616, 0.588, 0.494))
add_box('body', 'hood_rear_cowl_gap_shadow', 1012, 0, 1287, 28, 1310, 28, (0.114, 0.114, 0.114))
add_box('body', 'front_apron_lower_shadow', 92, 0, 710, 28, 1280, 42, (0.616, 0.588, 0.494))
add_box('front_detail', 'front_license_plate_upper_screw_left', -8, -155, 730, 18, 24, 24, (0.851, 0.835, 0.784))
add_box('front_detail', 'front_license_plate_upper_screw_right', -8, 155, 730, 18, 24, 24, (0.851, 0.835, 0.784))
add_box('front_detail', 'front_license_plate_lower_screw_left', -8, -155, 585, 18, 24, 24, (0.851, 0.835, 0.784))
add_box('front_detail', 'front_license_plate_lower_screw_right', -8, 155, 585, 18, 24, 24, (0.851, 0.835, 0.784))
add_cylinder('front_detail', 'front_bumper_face_bolt_1', 4, -680, 558, 'x', 34, 20, (0.851, 0.835, 0.784))
add_cylinder('front_detail', 'front_bumper_face_bolt_2', 4, -485, 558, 'x', 34, 20, (0.851, 0.835, 0.784))
add_cylinder('front_detail', 'front_bumper_face_bolt_3', 4, 485, 558, 'x', 34, 20, (0.851, 0.835, 0.784))
add_cylinder('front_detail', 'front_bumper_face_bolt_4', 4, 680, 558, 'x', 34, 20, (0.851, 0.835, 0.784))
add_cylinder('body', 'rear_bumper_face_bolt_1', 3742, -660, 558, 'x', 34, 20, (0.851, 0.835, 0.784))
add_cylinder('body', 'rear_bumper_face_bolt_2', 3742, -360, 558, 'x', 34, 20, (0.851, 0.835, 0.784))
add_cylinder('body', 'rear_bumper_face_bolt_3', 3742, 360, 558, 'x', 34, 20, (0.851, 0.835, 0.784))
add_cylinder('body', 'rear_bumper_face_bolt_4', 3742, 660, 558, 'x', 34, 20, (0.851, 0.835, 0.784))
add_cylinder('body', 'left_windshield_wiper_pivot', 1100, -358, 1372, 'x', 42, 26, (0.851, 0.835, 0.784))
add_box('body', 'left_windshield_wiper_blade_rubber', 1092, -165, 1508, 24, 480, 16, (0.114, 0.114, 0.114))
add_box('body', 'left_windshield_wiper_arm_chrome', 1094, -252, 1456, 18, 340, 14, (0.851, 0.835, 0.784))
add_cylinder('body', 'left_cowl_vent_screw_front', 1044, -278, 1360, 'z', 20, 12, (0.851, 0.835, 0.784))
add_cylinder('body', 'left_cowl_vent_screw_rear', 1018, -422, 1360, 'z', 20, 12, (0.851, 0.835, 0.784))
add_box('body', 'left_hood_side_gap_shadow', 420, -684, 1235, 760, 24, 24, (0.616, 0.588, 0.494))
add_cylinder('body', 'left_hood_latch_round_pin', 820, -645, 1238, 'y', 28, 22, (0.851, 0.835, 0.784))
add_cylinder('front_detail', 'left_front_fender_turn_signal_screw_front', 238, -642, 1078, 'z', 18, 12, (0.851, 0.835, 0.784))
add_cylinder('front_detail', 'left_front_fender_turn_signal_screw_rear', 350, -642, 1078, 'z', 18, 12, (0.851, 0.835, 0.784))
add_cylinder('front_detail', 'left_side_marker_chrome_bezel', 190, -682, 1005, 'y', 112, 18, (0.851, 0.835, 0.784))
add_cylinder('front_detail', 'left_fog_lamp_inner_glass', 16, -360, 620, 'x', 118, 18, (0.894, 0.863, 0.780))
add_box('front_detail', 'left_fog_lamp_drop_bracket', 42, -360, 548, 38, 34, 85, (0.176, 0.188, 0.200))
add_cylinder('body', 'left_mirror_mount_screw_1', 1328, -842, 1248, 'y', 20, 16, (0.851, 0.835, 0.784))
add_cylinder('body', 'left_mirror_mount_screw_2', 1328, -842, 1142, 'y', 20, 16, (0.851, 0.835, 0.784))
add_cylinder('body', 'left_mirror_mount_screw_3', 1484, -842, 1248, 'y', 20, 16, (0.851, 0.835, 0.784))
add_cylinder('body', 'left_mirror_mount_screw_4', 1484, -842, 1142, 'y', 20, 16, (0.851, 0.835, 0.784))
add_box('body', 'left_door_handle_shadow_gap', 1575, -834, 1016, 175, 18, 18, (0.616, 0.588, 0.494))
add_box('body', 'left_door_handle_chrome_face', 1575, -858, 1055, 140, 18, 22, (0.851, 0.835, 0.784))
add_box('body', 'left_front_door_lower_weather_strip', 1228, -836, 742, 760, 20, 22, (0.114, 0.114, 0.114))
add_box('body', 'left_rear_quarter_vertical_rear_seam', 2828, -832, 980, 24, 20, 560, (0.114, 0.114, 0.114))
add_cylinder('body', 'left_fuel_filler_outer_ring', 2935, -842, 1065, 'y', 145, 18, (0.851, 0.835, 0.784))
add_cylinder('hard_top', 'left_roof_gutter_rivet_1', 1240, -864, 1828, 'y', 18, 16, (0.851, 0.835, 0.784))
add_cylinder('hard_top', 'left_roof_gutter_rivet_2', 1485, -864, 1828, 'y', 18, 16, (0.851, 0.835, 0.784))
add_cylinder('hard_top', 'left_roof_gutter_rivet_3', 1730, -864, 1828, 'y', 18, 16, (0.851, 0.835, 0.784))
add_cylinder('hard_top', 'left_roof_gutter_rivet_4', 1975, -864, 1828, 'y', 18, 16, (0.851, 0.835, 0.784))
add_cylinder('hard_top', 'left_roof_gutter_rivet_5', 2220, -864, 1828, 'y', 18, 16, (0.851, 0.835, 0.784))
add_cylinder('hard_top', 'left_roof_gutter_rivet_6', 2465, -864, 1828, 'y', 18, 16, (0.851, 0.835, 0.784))
add_cylinder('hard_top', 'left_roof_gutter_rivet_7', 2710, -864, 1828, 'y', 18, 16, (0.851, 0.835, 0.784))
add_cylinder('hard_top', 'left_roof_gutter_rivet_8', 2955, -864, 1828, 'y', 18, 16, (0.851, 0.835, 0.784))
add_cylinder('hard_top', 'left_roof_gutter_rivet_9', 3200, -864, 1828, 'y', 18, 16, (0.851, 0.835, 0.784))
add_cylinder('hard_top', 'left_hardtop_front_window_upper_screw_1', 1240, -870, 1724, 'y', 18, 16, (0.851, 0.835, 0.784))
add_cylinder('hard_top', 'left_hardtop_front_window_lower_screw_1', 1240, -870, 1368, 'y', 18, 16, (0.851, 0.835, 0.784))
add_cylinder('hard_top', 'left_hardtop_front_window_upper_screw_2', 1600, -870, 1724, 'y', 18, 16, (0.851, 0.835, 0.784))
add_cylinder('hard_top', 'left_hardtop_front_window_lower_screw_2', 1600, -870, 1368, 'y', 18, 16, (0.851, 0.835, 0.784))
add_box('hard_top', 'left_hardtop_front_window_center_track', 1420, -868, 1435, 430, 14, 18, (0.851, 0.835, 0.784))
add_cylinder('hard_top', 'left_hardtop_rear_window_upper_screw_1', 1955, -870, 1724, 'y', 18, 16, (0.851, 0.835, 0.784))
add_cylinder('hard_top', 'left_hardtop_rear_window_lower_screw_1', 1955, -870, 1368, 'y', 18, 16, (0.851, 0.835, 0.784))
add_cylinder('hard_top', 'left_hardtop_rear_window_upper_screw_2', 2425, -870, 1724, 'y', 18, 16, (0.851, 0.835, 0.784))
add_cylinder('hard_top', 'left_hardtop_rear_window_lower_screw_2', 2425, -870, 1368, 'y', 18, 16, (0.851, 0.835, 0.784))
add_box('hard_top', 'left_hardtop_rear_window_center_track', 2190, -868, 1435, 540, 14, 18, (0.851, 0.835, 0.784))
add_box('hard_top', 'left_roof_gutter_front_end_cap', 1128, -862, 1812, 52, 34, 42, (0.851, 0.835, 0.784))
add_box('hard_top', 'left_roof_gutter_rear_end_cap', 3358, -862, 1812, 52, 34, 42, (0.851, 0.835, 0.784))
add_box('running_gear', 'front_left_rim_vent_slot_1', 877.894, -860, 477.5, 54, 20, 34, (0.149, 0.220, 0.247))
add_box('running_gear', 'front_left_rim_vent_slot_2', 735, -860, 560, 54, 20, 34, (0.149, 0.220, 0.247))
add_box('running_gear', 'front_left_rim_vent_slot_3', 592.106, -860, 477.5, 54, 20, 34, (0.149, 0.220, 0.247))
add_box('running_gear', 'front_left_rim_vent_slot_4', 592.106, -860, 312.5, 54, 20, 34, (0.149, 0.220, 0.247))
add_box('running_gear', 'front_left_rim_vent_slot_5', 735, -860, 230, 54, 20, 34, (0.149, 0.220, 0.247))
add_box('running_gear', 'front_left_rim_vent_slot_6', 877.894, -860, 312.5, 54, 20, 34, (0.149, 0.220, 0.247))
add_box('running_gear', 'front_left_tire_sidewall_tick_1', 1059.55, -865, 481.963, 38, 18, 18, (0.616, 0.588, 0.494))
add_box('running_gear', 'front_left_tire_sidewall_tick_2', 972.588, -865, 632.588, 38, 18, 18, (0.616, 0.588, 0.494))
add_box('running_gear', 'front_left_tire_sidewall_tick_3', 821.963, -865, 719.551, 38, 18, 18, (0.616, 0.588, 0.494))
add_box('running_gear', 'front_left_tire_sidewall_tick_4', 648.037, -865, 719.551, 38, 18, 18, (0.616, 0.588, 0.494))
add_box('running_gear', 'front_left_tire_sidewall_tick_5', 497.412, -865, 632.588, 38, 18, 18, (0.616, 0.588, 0.494))
add_box('running_gear', 'front_left_tire_sidewall_tick_6', 410.449, -865, 481.963, 38, 18, 18, (0.616, 0.588, 0.494))
add_box('running_gear', 'front_left_tire_sidewall_tick_7', 410.449, -865, 308.037, 38, 18, 18, (0.616, 0.588, 0.494))
add_box('running_gear', 'front_left_tire_sidewall_tick_8', 497.412, -865, 157.412, 38, 18, 18, (0.616, 0.588, 0.494))
add_box('running_gear', 'front_left_tire_sidewall_tick_9', 648.037, -865, 70.4489, 38, 18, 18, (0.616, 0.588, 0.494))
add_box('running_gear', 'front_left_tire_sidewall_tick_10', 821.963, -865, 70.4489, 38, 18, 18, (0.616, 0.588, 0.494))
add_box('running_gear', 'front_left_tire_sidewall_tick_11', 972.588, -865, 157.412, 38, 18, 18, (0.616, 0.588, 0.494))
add_box('running_gear', 'front_left_tire_sidewall_tick_12', 1059.55, -865, 308.037, 38, 18, 18, (0.616, 0.588, 0.494))
add_cylinder('running_gear', 'front_left_hub_cap_center_button', 735, -908, 395, 'y', 74, 24, (0.851, 0.835, 0.784))
add_box('running_gear', 'rear_left_rim_vent_slot_1', 3162.89, -860, 477.5, 54, 20, 34, (0.149, 0.220, 0.247))
add_box('running_gear', 'rear_left_rim_vent_slot_2', 3020, -860, 560, 54, 20, 34, (0.149, 0.220, 0.247))
add_box('running_gear', 'rear_left_rim_vent_slot_3', 2877.11, -860, 477.5, 54, 20, 34, (0.149, 0.220, 0.247))
add_box('running_gear', 'rear_left_rim_vent_slot_4', 2877.11, -860, 312.5, 54, 20, 34, (0.149, 0.220, 0.247))
add_box('running_gear', 'rear_left_rim_vent_slot_5', 3020, -860, 230, 54, 20, 34, (0.149, 0.220, 0.247))
add_box('running_gear', 'rear_left_rim_vent_slot_6', 3162.89, -860, 312.5, 54, 20, 34, (0.149, 0.220, 0.247))
add_box('running_gear', 'rear_left_tire_sidewall_tick_1', 3344.55, -865, 481.963, 38, 18, 18, (0.616, 0.588, 0.494))
add_box('running_gear', 'rear_left_tire_sidewall_tick_2', 3257.59, -865, 632.588, 38, 18, 18, (0.616, 0.588, 0.494))
add_box('running_gear', 'rear_left_tire_sidewall_tick_3', 3106.96, -865, 719.551, 38, 18, 18, (0.616, 0.588, 0.494))
add_box('running_gear', 'rear_left_tire_sidewall_tick_4', 2933.04, -865, 719.551, 38, 18, 18, (0.616, 0.588, 0.494))
add_box('running_gear', 'rear_left_tire_sidewall_tick_5', 2782.41, -865, 632.588, 38, 18, 18, (0.616, 0.588, 0.494))
add_box('running_gear', 'rear_left_tire_sidewall_tick_6', 2695.45, -865, 481.963, 38, 18, 18, (0.616, 0.588, 0.494))
add_box('running_gear', 'rear_left_tire_sidewall_tick_7', 2695.45, -865, 308.037, 38, 18, 18, (0.616, 0.588, 0.494))
add_box('running_gear', 'rear_left_tire_sidewall_tick_8', 2782.41, -865, 157.412, 38, 18, 18, (0.616, 0.588, 0.494))
add_box('running_gear', 'rear_left_tire_sidewall_tick_9', 2933.04, -865, 70.4489, 38, 18, 18, (0.616, 0.588, 0.494))
add_box('running_gear', 'rear_left_tire_sidewall_tick_10', 3106.96, -865, 70.4489, 38, 18, 18, (0.616, 0.588, 0.494))
add_box('running_gear', 'rear_left_tire_sidewall_tick_11', 3257.59, -865, 157.412, 38, 18, 18, (0.616, 0.588, 0.494))
add_box('running_gear', 'rear_left_tire_sidewall_tick_12', 3344.55, -865, 308.037, 38, 18, 18, (0.616, 0.588, 0.494))
add_cylinder('running_gear', 'rear_left_hub_cap_center_button', 3020, -908, 395, 'y', 74, 24, (0.851, 0.835, 0.784))
add_cylinder('body', 'right_windshield_wiper_pivot', 1100, 358, 1372, 'x', 42, 26, (0.851, 0.835, 0.784))
add_box('body', 'right_windshield_wiper_blade_rubber', 1092, 165, 1508, 24, 480, 16, (0.114, 0.114, 0.114))
add_box('body', 'right_windshield_wiper_arm_chrome', 1094, 252, 1456, 18, 340, 14, (0.851, 0.835, 0.784))
add_cylinder('body', 'right_cowl_vent_screw_front', 1044, 278, 1360, 'z', 20, 12, (0.851, 0.835, 0.784))
add_cylinder('body', 'right_cowl_vent_screw_rear', 1018, 422, 1360, 'z', 20, 12, (0.851, 0.835, 0.784))
add_box('body', 'right_hood_side_gap_shadow', 420, 684, 1235, 760, 24, 24, (0.616, 0.588, 0.494))
add_cylinder('body', 'right_hood_latch_round_pin', 820, 645, 1238, 'y', 28, 22, (0.851, 0.835, 0.784))
add_cylinder('front_detail', 'right_front_fender_turn_signal_screw_front', 238, 642, 1078, 'z', 18, 12, (0.851, 0.835, 0.784))
add_cylinder('front_detail', 'right_front_fender_turn_signal_screw_rear', 350, 642, 1078, 'z', 18, 12, (0.851, 0.835, 0.784))
add_cylinder('front_detail', 'right_side_marker_chrome_bezel', 190, 682, 1005, 'y', 112, 18, (0.851, 0.835, 0.784))
add_cylinder('front_detail', 'right_fog_lamp_inner_glass', 16, 360, 620, 'x', 118, 18, (0.894, 0.863, 0.780))
add_box('front_detail', 'right_fog_lamp_drop_bracket', 42, 360, 548, 38, 34, 85, (0.176, 0.188, 0.200))
add_cylinder('body', 'right_mirror_mount_screw_1', 1328, 842, 1248, 'y', 20, 16, (0.851, 0.835, 0.784))
add_cylinder('body', 'right_mirror_mount_screw_2', 1328, 842, 1142, 'y', 20, 16, (0.851, 0.835, 0.784))
add_cylinder('body', 'right_mirror_mount_screw_3', 1484, 842, 1248, 'y', 20, 16, (0.851, 0.835, 0.784))
add_cylinder('body', 'right_mirror_mount_screw_4', 1484, 842, 1142, 'y', 20, 16, (0.851, 0.835, 0.784))
add_box('body', 'right_door_handle_shadow_gap', 1575, 834, 1016, 175, 18, 18, (0.616, 0.588, 0.494))
add_box('body', 'right_door_handle_chrome_face', 1575, 858, 1055, 140, 18, 22, (0.851, 0.835, 0.784))
add_box('body', 'right_front_door_lower_weather_strip', 1228, 836, 742, 760, 20, 22, (0.114, 0.114, 0.114))
add_box('body', 'right_rear_quarter_vertical_rear_seam', 2828, 832, 980, 24, 20, 560, (0.114, 0.114, 0.114))
add_cylinder('body', 'right_fuel_filler_outer_ring', 2935, 842, 1065, 'y', 145, 18, (0.851, 0.835, 0.784))
add_cylinder('hard_top', 'right_roof_gutter_rivet_1', 1240, 864, 1828, 'y', 18, 16, (0.851, 0.835, 0.784))
add_cylinder('hard_top', 'right_roof_gutter_rivet_2', 1485, 864, 1828, 'y', 18, 16, (0.851, 0.835, 0.784))
add_cylinder('hard_top', 'right_roof_gutter_rivet_3', 1730, 864, 1828, 'y', 18, 16, (0.851, 0.835, 0.784))
add_cylinder('hard_top', 'right_roof_gutter_rivet_4', 1975, 864, 1828, 'y', 18, 16, (0.851, 0.835, 0.784))
add_cylinder('hard_top', 'right_roof_gutter_rivet_5', 2220, 864, 1828, 'y', 18, 16, (0.851, 0.835, 0.784))
add_cylinder('hard_top', 'right_roof_gutter_rivet_6', 2465, 864, 1828, 'y', 18, 16, (0.851, 0.835, 0.784))
add_cylinder('hard_top', 'right_roof_gutter_rivet_7', 2710, 864, 1828, 'y', 18, 16, (0.851, 0.835, 0.784))
add_cylinder('hard_top', 'right_roof_gutter_rivet_8', 2955, 864, 1828, 'y', 18, 16, (0.851, 0.835, 0.784))
add_cylinder('hard_top', 'right_roof_gutter_rivet_9', 3200, 864, 1828, 'y', 18, 16, (0.851, 0.835, 0.784))
add_cylinder('hard_top', 'right_hardtop_front_window_upper_screw_1', 1240, 870, 1724, 'y', 18, 16, (0.851, 0.835, 0.784))
add_cylinder('hard_top', 'right_hardtop_front_window_lower_screw_1', 1240, 870, 1368, 'y', 18, 16, (0.851, 0.835, 0.784))
add_cylinder('hard_top', 'right_hardtop_front_window_upper_screw_2', 1600, 870, 1724, 'y', 18, 16, (0.851, 0.835, 0.784))
add_cylinder('hard_top', 'right_hardtop_front_window_lower_screw_2', 1600, 870, 1368, 'y', 18, 16, (0.851, 0.835, 0.784))
add_box('hard_top', 'right_hardtop_front_window_center_track', 1420, 868, 1435, 430, 14, 18, (0.851, 0.835, 0.784))
add_cylinder('hard_top', 'right_hardtop_rear_window_upper_screw_1', 1955, 870, 1724, 'y', 18, 16, (0.851, 0.835, 0.784))
add_cylinder('hard_top', 'right_hardtop_rear_window_lower_screw_1', 1955, 870, 1368, 'y', 18, 16, (0.851, 0.835, 0.784))
add_cylinder('hard_top', 'right_hardtop_rear_window_upper_screw_2', 2425, 870, 1724, 'y', 18, 16, (0.851, 0.835, 0.784))
add_cylinder('hard_top', 'right_hardtop_rear_window_lower_screw_2', 2425, 870, 1368, 'y', 18, 16, (0.851, 0.835, 0.784))
add_box('hard_top', 'right_hardtop_rear_window_center_track', 2190, 868, 1435, 540, 14, 18, (0.851, 0.835, 0.784))
add_box('hard_top', 'right_roof_gutter_front_end_cap', 1128, 862, 1812, 52, 34, 42, (0.851, 0.835, 0.784))
add_box('hard_top', 'right_roof_gutter_rear_end_cap', 3358, 862, 1812, 52, 34, 42, (0.851, 0.835, 0.784))
add_box('running_gear', 'front_right_rim_vent_slot_1', 877.894, 860, 477.5, 54, 20, 34, (0.149, 0.220, 0.247))
add_box('running_gear', 'front_right_rim_vent_slot_2', 735, 860, 560, 54, 20, 34, (0.149, 0.220, 0.247))
add_box('running_gear', 'front_right_rim_vent_slot_3', 592.106, 860, 477.5, 54, 20, 34, (0.149, 0.220, 0.247))
add_box('running_gear', 'front_right_rim_vent_slot_4', 592.106, 860, 312.5, 54, 20, 34, (0.149, 0.220, 0.247))
add_box('running_gear', 'front_right_rim_vent_slot_5', 735, 860, 230, 54, 20, 34, (0.149, 0.220, 0.247))
add_box('running_gear', 'front_right_rim_vent_slot_6', 877.894, 860, 312.5, 54, 20, 34, (0.149, 0.220, 0.247))
add_box('running_gear', 'front_right_tire_sidewall_tick_1', 1059.55, 865, 481.963, 38, 18, 18, (0.616, 0.588, 0.494))
add_box('running_gear', 'front_right_tire_sidewall_tick_2', 972.588, 865, 632.588, 38, 18, 18, (0.616, 0.588, 0.494))
add_box('running_gear', 'front_right_tire_sidewall_tick_3', 821.963, 865, 719.551, 38, 18, 18, (0.616, 0.588, 0.494))
add_box('running_gear', 'front_right_tire_sidewall_tick_4', 648.037, 865, 719.551, 38, 18, 18, (0.616, 0.588, 0.494))
add_box('running_gear', 'front_right_tire_sidewall_tick_5', 497.412, 865, 632.588, 38, 18, 18, (0.616, 0.588, 0.494))
add_box('running_gear', 'front_right_tire_sidewall_tick_6', 410.449, 865, 481.963, 38, 18, 18, (0.616, 0.588, 0.494))
add_box('running_gear', 'front_right_tire_sidewall_tick_7', 410.449, 865, 308.037, 38, 18, 18, (0.616, 0.588, 0.494))
add_box('running_gear', 'front_right_tire_sidewall_tick_8', 497.412, 865, 157.412, 38, 18, 18, (0.616, 0.588, 0.494))
add_box('running_gear', 'front_right_tire_sidewall_tick_9', 648.037, 865, 70.4489, 38, 18, 18, (0.616, 0.588, 0.494))
add_box('running_gear', 'front_right_tire_sidewall_tick_10', 821.963, 865, 70.4489, 38, 18, 18, (0.616, 0.588, 0.494))
add_box('running_gear', 'front_right_tire_sidewall_tick_11', 972.588, 865, 157.412, 38, 18, 18, (0.616, 0.588, 0.494))
add_box('running_gear', 'front_right_tire_sidewall_tick_12', 1059.55, 865, 308.037, 38, 18, 18, (0.616, 0.588, 0.494))
add_cylinder('running_gear', 'front_right_hub_cap_center_button', 735, 908, 395, 'y', 74, 24, (0.851, 0.835, 0.784))
add_box('running_gear', 'rear_right_rim_vent_slot_1', 3162.89, 860, 477.5, 54, 20, 34, (0.149, 0.220, 0.247))
add_box('running_gear', 'rear_right_rim_vent_slot_2', 3020, 860, 560, 54, 20, 34, (0.149, 0.220, 0.247))
add_box('running_gear', 'rear_right_rim_vent_slot_3', 2877.11, 860, 477.5, 54, 20, 34, (0.149, 0.220, 0.247))
add_box('running_gear', 'rear_right_rim_vent_slot_4', 2877.11, 860, 312.5, 54, 20, 34, (0.149, 0.220, 0.247))
add_box('running_gear', 'rear_right_rim_vent_slot_5', 3020, 860, 230, 54, 20, 34, (0.149, 0.220, 0.247))
add_box('running_gear', 'rear_right_rim_vent_slot_6', 3162.89, 860, 312.5, 54, 20, 34, (0.149, 0.220, 0.247))
add_box('running_gear', 'rear_right_tire_sidewall_tick_1', 3344.55, 865, 481.963, 38, 18, 18, (0.616, 0.588, 0.494))
add_box('running_gear', 'rear_right_tire_sidewall_tick_2', 3257.59, 865, 632.588, 38, 18, 18, (0.616, 0.588, 0.494))
add_box('running_gear', 'rear_right_tire_sidewall_tick_3', 3106.96, 865, 719.551, 38, 18, 18, (0.616, 0.588, 0.494))
add_box('running_gear', 'rear_right_tire_sidewall_tick_4', 2933.04, 865, 719.551, 38, 18, 18, (0.616, 0.588, 0.494))
add_box('running_gear', 'rear_right_tire_sidewall_tick_5', 2782.41, 865, 632.588, 38, 18, 18, (0.616, 0.588, 0.494))
add_box('running_gear', 'rear_right_tire_sidewall_tick_6', 2695.45, 865, 481.963, 38, 18, 18, (0.616, 0.588, 0.494))
add_box('running_gear', 'rear_right_tire_sidewall_tick_7', 2695.45, 865, 308.037, 38, 18, 18, (0.616, 0.588, 0.494))
add_box('running_gear', 'rear_right_tire_sidewall_tick_8', 2782.41, 865, 157.412, 38, 18, 18, (0.616, 0.588, 0.494))
add_box('running_gear', 'rear_right_tire_sidewall_tick_9', 2933.04, 865, 70.4489, 38, 18, 18, (0.616, 0.588, 0.494))
add_box('running_gear', 'rear_right_tire_sidewall_tick_10', 3106.96, 865, 70.4489, 38, 18, 18, (0.616, 0.588, 0.494))
add_box('running_gear', 'rear_right_tire_sidewall_tick_11', 3257.59, 865, 157.412, 38, 18, 18, (0.616, 0.588, 0.494))
add_box('running_gear', 'rear_right_tire_sidewall_tick_12', 3344.55, 865, 308.037, 38, 18, 18, (0.616, 0.588, 0.494))
add_cylinder('running_gear', 'rear_right_hub_cap_center_button', 3020, 908, 395, 'y', 74, 24, (0.851, 0.835, 0.784))
add_box('hard_top', 'rear_window_upper_inner_shadow', 3492, 0, 1608, 20, 760, 24, (0.149, 0.220, 0.247))
add_box('hard_top', 'rear_window_lower_inner_shadow', 3492, 0, 1342, 20, 760, 24, (0.149, 0.220, 0.247))
add_box('hard_top', 'rear_door_hinge_mount_plate_1', 3528, -620, 1510, 24, 84, 96, (0.851, 0.835, 0.784))
add_box('hard_top', 'rear_door_hinge_mount_plate_2', 3528, -520, 1180, 24, 84, 96, (0.851, 0.835, 0.784))
add_box('hard_top', 'rear_door_hinge_mount_plate_3', 3528, 520, 1180, 24, 84, 96, (0.851, 0.835, 0.784))
add_box('hard_top', 'rear_door_hinge_mount_plate_4', 3528, 620, 1510, 24, 84, 96, (0.851, 0.835, 0.784))
add_cylinder('hard_top', 'rear_door_hinge_plate_screw_1', 3544, -590, 1555, 'x', 18, 16, (0.851, 0.835, 0.784))
add_cylinder('hard_top', 'rear_door_hinge_plate_screw_2', 3544, -590, 1470, 'x', 18, 16, (0.851, 0.835, 0.784))
add_cylinder('hard_top', 'rear_door_hinge_plate_screw_3', 3544, 590, 1555, 'x', 18, 16, (0.851, 0.835, 0.784))
add_cylinder('hard_top', 'rear_door_hinge_plate_screw_4', 3544, 590, 1470, 'x', 18, 16, (0.851, 0.835, 0.784))
add_cylinder('hard_top', 'rear_door_hinge_plate_screw_5', 3544, -590, 1225, 'x', 18, 16, (0.851, 0.835, 0.784))
add_cylinder('hard_top', 'rear_door_hinge_plate_screw_6', 3544, -590, 1138, 'x', 18, 16, (0.851, 0.835, 0.784))
add_cylinder('hard_top', 'rear_door_hinge_plate_screw_7', 3544, 590, 1225, 'x', 18, 16, (0.851, 0.835, 0.784))
add_cylinder('hard_top', 'rear_door_hinge_plate_screw_8', 3544, 590, 1138, 'x', 18, 16, (0.851, 0.835, 0.784))
add_box('body', 'rear_spare_carrier_latch_plate', 3530, 315, 1042, 36, 132, 92, (0.722, 0.722, 0.722))
add_cylinder('body', 'rear_spare_carrier_latch_pin', 3552, 315, 1042, 'x', 28, 36, (0.851, 0.835, 0.784))
add_box('body', 'rear_spare_carrier_lower_hinge_plate', 3528, -320, 760, 36, 126, 88, (0.722, 0.722, 0.722))
add_box('body', 'rear_spare_carrier_upper_hinge_plate', 3528, -320, 1088, 36, 126, 88, (0.722, 0.722, 0.722))
add_cylinder('body', 'rear_spare_carrier_hardware_screw_1', 3550, -320, 724, 'x', 18, 16, (0.851, 0.835, 0.784))
add_cylinder('body', 'rear_spare_carrier_hardware_screw_2', 3550, -320, 796, 'x', 18, 16, (0.851, 0.835, 0.784))
add_cylinder('body', 'rear_spare_carrier_hardware_screw_3', 3550, -320, 1052, 'x', 18, 16, (0.851, 0.835, 0.784))
add_cylinder('body', 'rear_spare_carrier_hardware_screw_4', 3550, -320, 1124, 'x', 18, 16, (0.851, 0.835, 0.784))
add_cylinder('body', 'rear_spare_carrier_hardware_screw_5', 3550, 315, 1006, 'x', 18, 16, (0.851, 0.835, 0.784))
add_cylinder('body', 'rear_spare_carrier_hardware_screw_6', 3550, 315, 1078, 'x', 18, 16, (0.851, 0.835, 0.784))
add_box('body', 'rear_license_plate_upper_lamp_left', 3508, -145, 810, 28, 90, 34, (0.851, 0.835, 0.784))
add_box('body', 'rear_license_plate_upper_lamp_right', 3508, 145, 810, 28, 90, 34, (0.851, 0.835, 0.784))
add_cylinder('body', 'rear_license_plate_screw_1', 3534, -160, 770, 'x', 18, 16, (0.851, 0.835, 0.784))
add_cylinder('body', 'rear_license_plate_screw_2', 3534, 160, 770, 'x', 18, 16, (0.851, 0.835, 0.784))
add_cylinder('body', 'rear_license_plate_screw_3', 3534, -160, 630, 'x', 18, 16, (0.851, 0.835, 0.784))
add_cylinder('body', 'rear_license_plate_screw_4', 3534, 160, 630, 'x', 18, 16, (0.851, 0.835, 0.784))
add_cylinder('body', 'rear_left_tail_lamp_chrome_bezel', 3488, -675, 930, 'x', 122, 18, (0.851, 0.835, 0.784))
add_cylinder('body', 'rear_left_tail_lamp_inner_lens', 3502, -675, 930, 'x', 72, 18, (0.839, 0.278, 0.216))
add_cylinder('body', 'rear_right_tail_lamp_chrome_bezel', 3488, 675, 930, 'x', 122, 18, (0.851, 0.835, 0.784))
add_cylinder('body', 'rear_right_tail_lamp_inner_lens', 3502, 675, 930, 'x', 72, 18, (0.839, 0.278, 0.216))
add_box('interior', 'dashboard_glovebox_door', 1212, 420, 1115, 35, 335, 150, (0.910, 0.910, 0.910))
add_box('interior', 'dash_instrument_cluster_plate', 1208, -420, 1128, 36, 330, 170, (0.910, 0.910, 0.910))
add_cylinder('interior', 'dash_switch_knob_1', 1200, -535, 1050, 'x', 34, 26, (0.722, 0.722, 0.722))
add_cylinder('interior', 'dash_switch_knob_2', 1200, -480, 1050, 'x', 34, 26, (0.722, 0.722, 0.722))
add_cylinder('interior', 'dash_switch_knob_3', 1200, -425, 1050, 'x', 34, 26, (0.722, 0.722, 0.722))
add_cylinder('interior', 'dash_switch_knob_4', 1200, -370, 1050, 'x', 34, 26, (0.722, 0.722, 0.722))
add_cylinder('interior', 'dash_switch_knob_5', 1200, -315, 1050, 'x', 34, 26, (0.722, 0.722, 0.722))
add_cylinder('interior', 'heater_control_knob_1', 1200, 90, 1048, 'x', 30, 24, (0.722, 0.722, 0.722))
add_cylinder('interior', 'heater_control_knob_2', 1200, 155, 1048, 'x', 30, 24, (0.722, 0.722, 0.722))
add_cylinder('interior', 'heater_control_knob_3', 1200, 220, 1048, 'x', 30, 24, (0.722, 0.722, 0.722))
add_cylinder('interior', 'heater_control_knob_4', 1200, 285, 1048, 'x', 30, 24, (0.722, 0.722, 0.722))
add_box('interior', 'steering_wheel_spoke_1', 1216, -510, 1205, 34, 170, 18, (0.722, 0.722, 0.722))
add_box('interior', 'steering_wheel_spoke_2', 1216, -420, 1205, 34, 170, 18, (0.722, 0.722, 0.722))
add_box('interior', 'steering_wheel_spoke_3', 1216, -330, 1205, 34, 170, 18, (0.722, 0.722, 0.722))
add_box('interior', 'clutch_pedal_pad', 1340, -520, 705, 90, 45, 110, (0.114, 0.114, 0.114))
add_cylinder('interior', 'clutch_pedal_arm', 1300, -520, 820, 'z', 22, 240, (0.722, 0.722, 0.722))
add_box('interior', 'brake_pedal_pad', 1340, -440, 705, 90, 45, 110, (0.114, 0.114, 0.114))
add_cylinder('interior', 'brake_pedal_arm', 1300, -440, 820, 'z', 22, 240, (0.722, 0.722, 0.722))
add_box('interior', 'accelerator_pedal_pad', 1340, -350, 705, 90, 45, 110, (0.114, 0.114, 0.114))
add_cylinder('interior', 'accelerator_pedal_arm', 1300, -350, 820, 'z', 22, 240, (0.722, 0.722, 0.722))
add_box('interior', 'lhd_pedal_box_reinforcement', 1195, -465, 850, 95, 285, 250, (0.722, 0.722, 0.722))
add_box('interior', 'lhd_steering_column_dash_bracket', 1215, -420, 1040, 62, 210, 66, (0.722, 0.722, 0.722))
add_cylinder('interior', 'steering_column_firewall_boot', 1142, -420, 1020, 'x', 130, 48, (0.114, 0.114, 0.114))
add_cylinder('interior', 'brake_pedal_pivot_bar', 1260, -440, 960, 'y', 32, 180, (0.722, 0.722, 0.722))
add_cylinder('interior', 'clutch_pedal_pivot_bar', 1260, -520, 960, 'y', 32, 170, (0.722, 0.722, 0.722))
add_box('interior', 'accelerator_linkage_pivot', 1225, -325, 875, 52, 42, 125, (0.722, 0.722, 0.722))
add_cylinder('interior', 'steering_column_indicator_stalk', 1225, -605, 1220, 'y', 22, 165, (0.722, 0.722, 0.722))
add_box('interior', 'driver_side_floor_dimmer_switch', 1290, -650, 735, 70, 55, 34, (0.114, 0.114, 0.114))
add_cylinder('interior', 'handbrake_lever', 1760, -250, 790, 'z', 32, 360, (0.722, 0.722, 0.722))
add_cylinder('interior', 'gearshift_knob', 1500, -35, 1160, 'z', 86, 60, (0.114, 0.114, 0.114))
add_cylinder('interior', 'transfer_case_knob', 1580, -120, 1110, 'z', 76, 55, (0.114, 0.114, 0.114))
add_box('interior', 'front_left_seat_left_rail', 1515, -420, 675, 545, 36, 42, (0.722, 0.722, 0.722))
add_box('interior', 'front_left_seat_right_rail', 1515, -720, 675, 545, 36, 42, (0.722, 0.722, 0.722))
add_box('interior', 'rear_left_seat_left_rail', 2350, -420, 675, 545, 36, 42, (0.722, 0.722, 0.722))
add_box('interior', 'rear_left_seat_right_rail', 2350, -720, 675, 545, 36, 42, (0.722, 0.722, 0.722))
add_box('interior', 'left_front_seat_belt_buckle', 1730, -90, 850, 62, 42, 145, (0.839, 0.278, 0.216))
add_box('interior', 'left_front_seat_back_seam', 1848, -310, 1080, 24, 390, 28, (0.114, 0.114, 0.114))
add_box('interior', 'left_front_floor_mat', 1350, -310, 723, 760, 500, 22, (0.114, 0.114, 0.114))
add_box('interior', 'front_right_seat_left_rail', 1515, 420, 675, 545, 36, 42, (0.722, 0.722, 0.722))
add_box('interior', 'front_right_seat_right_rail', 1515, 720, 675, 545, 36, 42, (0.722, 0.722, 0.722))
add_box('interior', 'rear_right_seat_left_rail', 2350, 420, 675, 545, 36, 42, (0.722, 0.722, 0.722))
add_box('interior', 'rear_right_seat_right_rail', 2350, 720, 675, 545, 36, 42, (0.722, 0.722, 0.722))
add_box('interior', 'right_front_seat_belt_buckle', 1730, 90, 850, 62, 42, 145, (0.839, 0.278, 0.216))
add_box('interior', 'right_front_seat_back_seam', 1848, 310, 1080, 24, 390, 28, (0.114, 0.114, 0.114))
add_box('interior', 'right_front_floor_mat', 1350, 310, 723, 760, 500, 22, (0.114, 0.114, 0.114))
add_box('interior', 'rear_floor_mat', 2220, 0, 748, 1050, 1020, 22, (0.114, 0.114, 0.114))
add_box('interior', 'rear_bench_seat_seam', 2510, 0, 845, 610, 1010, 24, (0.114, 0.114, 0.114))
add_cylinder('engine_bay', 'cooling_fan_hub', 300, 0, 1010, 'x', 135, 62, (0.722, 0.722, 0.722))
add_box('engine_bay', 'cooling_fan_blade_1', 286, 210, 992, 38, 250, 36, (0.722, 0.722, 0.722))
add_box('engine_bay', 'cooling_fan_blade_2', 286, 105, 1173.87, 38, 250, 36, (0.722, 0.722, 0.722))
add_box('engine_bay', 'cooling_fan_blade_3', 286, -105, 1173.87, 38, 250, 36, (0.722, 0.722, 0.722))
add_box('engine_bay', 'cooling_fan_blade_4', 286, -210, 992, 38, 250, 36, (0.722, 0.722, 0.722))
add_box('engine_bay', 'cooling_fan_blade_5', 286, -105, 810.135, 38, 250, 36, (0.722, 0.722, 0.722))
add_box('engine_bay', 'cooling_fan_blade_6', 286, 105, 810.135, 38, 250, 36, (0.722, 0.722, 0.722))
add_cylinder('engine_bay', 'crank_pulley', 385, 0, 850, 'x', 145, 60, (0.722, 0.722, 0.722))
add_cylinder('engine_bay', 'water_pump_pulley', 360, 0, 1010, 'x', 125, 54, (0.722, 0.722, 0.722))
add_box('engine_bay', 'fan_belt_upper_run', 350, 0, 1010, 26, 38, 270, (0.114, 0.114, 0.114))
add_box('engine_bay', 'fan_belt_lower_run', 385, 0, 850, 26, 38, 235, (0.114, 0.114, 0.114))
add_cylinder('engine_bay', 'alternator_body', 565, 325, 1010, 'x', 190, 220, (0.722, 0.722, 0.722))
add_cylinder('engine_bay', 'starter_motor', 730, 265, 680, 'x', 155, 310, (0.722, 0.722, 0.722))
add_box('engine_bay', 'intake_manifold', 560, -260, 995, 460, 90, 115, (0.722, 0.722, 0.722))
add_box('engine_bay', 'exhaust_manifold', 575, 260, 900, 500, 95, 145, (0.247, 0.259, 0.271))
add_cylinder('engine_bay', 'carburetor_body', 745, -220, 1165, 'z', 120, 170, (0.722, 0.722, 0.722))
add_cylinder('engine_bay', 'round_air_cleaner_lid', 760, -235, 1250, 'z', 260, 68, (0.722, 0.722, 0.722))
add_cylinder('engine_bay', 'brake_booster', 1075, -520, 1060, 'x', 260, 145, (0.722, 0.722, 0.722))
add_cylinder('engine_bay', 'master_cylinder', 945, -520, 1060, 'x', 92, 230, (0.722, 0.722, 0.722))
add_box('engine_bay', 'clutch_master_cylinder', 945, -350, 1035, 210, 82, 76, (0.722, 0.722, 0.722))
add_box('engine_bay', 'lhd_firewall_pedal_box_outer_plate', 1112, -475, 895, 42, 350, 300, (0.722, 0.722, 0.722))
add_box('engine_bay', 'brake_booster_firewall_bracket', 1110, -520, 1015, 48, 300, 250, (0.722, 0.722, 0.722))
add_cylinder('engine_bay', 'brake_master_reservoir', 875, -520, 1165, 'z', 110, 105, (0.910, 0.910, 0.910))
add_cylinder('engine_bay', 'brake_master_reservoir_cap', 875, -520, 1225, 'z', 82, 24, (0.769, 0.604, 0.239))
add_cylinder('engine_bay', 'brake_booster_vacuum_hose', 820, -430, 1130, 'x', 34, 470, (0.114, 0.114, 0.114))
add_cylinder('engine_bay', 'clutch_master_reservoir_cap', 910, -350, 1130, 'z', 70, 26, (0.769, 0.604, 0.239))
add_cylinder('engine_bay', 'clutch_hydraulic_line_firewall_run', 830, -350, 980, 'x', 14, 520, (0.722, 0.722, 0.722))
add_cylinder('engine_bay', 'steering_column_lower_firewall_shaft', 1010, -420, 980, 'x', 44, 340, (0.722, 0.722, 0.722))
add_cylinder('engine_bay', 'steering_column_lower_universal_joint', 840, -430, 955, 'x', 76, 58, (0.722, 0.722, 0.722))
add_cylinder('engine_bay', 'steering_intermediate_shaft', 690, -455, 850, 'x', 40, 360, (0.722, 0.722, 0.722))
add_box('engine_bay', 'battery_case', 570, 430, 765, 310, 205, 205, (0.114, 0.114, 0.114))
add_cylinder('engine_bay', 'battery_positive_terminal', 622, 355, 985, 'z', 34, 46, (0.839, 0.278, 0.216))
add_cylinder('engine_bay', 'battery_negative_terminal', 812, 505, 985, 'z', 34, 46, (0.722, 0.722, 0.722))
add_cylinder('engine_bay', 'positive_battery_cable_run', 710, 405, 1015, 'x', 24, 520, (0.839, 0.278, 0.216))
add_cylinder('engine_bay', 'radiator_top_tank', 205, 0, 1095, 'y', 95, 1030, (0.722, 0.722, 0.722))
add_cylinder('engine_bay', 'radiator_bottom_tank', 205, 0, 720, 'y', 85, 1030, (0.722, 0.722, 0.722))
add_cylinder('engine_bay', 'radiator_cap', 218, 260, 1155, 'z', 54, 36, (0.769, 0.604, 0.239))
add_box('engine_bay', 'washer_bottle', 795, 535, 850, 160, 105, 210, (0.910, 0.910, 0.910))
add_box('engine_bay', 'engine_bay_fuse_relay_board_reference', 930, 610, 930, 240, 75, 220, (0.839, 0.278, 0.216))
add_cylinder('engine_bay', 'dipstick_loop', 840, 130, 1030, 'z', 46, 28, (0.769, 0.604, 0.239))
add_box('fuel_system', 'rear_underfloor_fuel_tank', 2870, 0, 405, 650, 930, 260, (0.310, 0.498, 0.333))
add_box('fuel_system', 'fuel_tank_retaining_strap_1', 2780, 0, 555, 42, 980, 38, (0.722, 0.722, 0.722))
add_box('fuel_system', 'fuel_tank_retaining_strap_2', 3020, 0, 555, 42, 980, 38, (0.722, 0.722, 0.722))
add_cylinder('fuel_system', 'fuel_filler_neck', 3000, -690, 940, 'z', 76, 410, (0.722, 0.722, 0.722))
add_cylinder('fuel_system', 'fuel_line_frame_run', 1880, 330, 560, 'x', 16, 2070, (0.769, 0.604, 0.239))
add_cylinder('exhaust', 'front_exhaust_pipe', 870, 310, 520, 'x', 68, 950, (0.722, 0.722, 0.722))
add_cylinder('exhaust', 'centre_exhaust_pipe', 1700, 330, 470, 'x', 68, 1020, (0.722, 0.722, 0.722))
add_cylinder('exhaust', 'rear_exhaust_pipe', 2750, 330, 470, 'x', 62, 1220, (0.722, 0.722, 0.722))
add_cylinder('exhaust', 'muffler_body', 2260, 330, 465, 'x', 250, 650, (0.722, 0.722, 0.722))
add_box('exhaust', 'exhaust_hanger_1', 1020, 330, 590, 52, 58, 135, (0.114, 0.114, 0.114))
add_box('exhaust', 'exhaust_hanger_2', 2180, 330, 590, 52, 58, 135, (0.114, 0.114, 0.114))
add_box('exhaust', 'exhaust_hanger_3', 3040, 330, 590, 52, 58, 135, (0.114, 0.114, 0.114))
add_cylinder('datum', 'wheelbase_datum_line_left', 1877.5, -925, 285, 'x', 18, 2285, (0.486, 0.435, 0.796))
add_cylinder('datum', 'wheelbase_datum_line_right', 1877.5, 925, 285, 'x', 18, 2285, (0.486, 0.435, 0.796))
add_cylinder('datum', 'front_track_datum_line', 735, 0, 260, 'y', 18, 1410, (0.486, 0.435, 0.796))
add_cylinder('datum', 'rear_track_datum_line', 3020, 0, 260, 'y', 18, 1410, (0.486, 0.435, 0.796))

doc.recompute()
Gui.SendMsgToActiveView('ViewFit') if Gui is not None else None
